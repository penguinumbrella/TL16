FME workspace parking_occupancy.fmw

Creator
    GEOMTYPE = Geometry Object
    NUM = 1
    CREATED -> West_Parkade_Latest_Timestamp [INITIATOR]
    CREATED -> North_Parkade_Latest_Timestamp [INITIATOR]
    CREATED -> Fraser_Parkade_Latest_Timestamp [INITIATOR]
    CREATED -> Thunderbird_Parkade_Latest_Timestamp [INITIATOR]
    CREATED -> RoseGarden_Parkade_Latest_Timestamp [INITIATOR]
    CREATED -> HealthSciences_Parkade_Latest_Timestamp [INITIATOR]
    CREATED -> UnivWstBlvd_Parkade_Latest_Timestamp [INITIATOR]
West_Parkade_Latest_Timestamp: SQLExecutor
    COMBINE_ATTRS = Result Attributes Only
    COMBINE_GEOM = Initiator Geometry Only
    DATASET = ServerTestDB
    EXPOSED_ATTRIBUTE_LIST = zone_id,latest_timestamp
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT = SELECT zone_id, MAX(TimestampUnix) AS latest_timestamp FROM Parking.dbo.WestParkade_Occupancy GROUP BY zone_id
    RESULT -> ReadNewOccupancy_WestParkade [INITIATOR]
ReadNewOccupancy_WestParkade: SQLExecutor
    COMBINE_ATTRS = Result Attributes Only
    COMBINE_GEOM = Initiator Geometry Only
    DATASET = Autovu_UBC
    EXPOSED_ATTRIBUTE_LIST = ZoneId,TimestampUtc,Timestamp,TimezoneId,Capacity,Vehicles,Violations,ViolationsEnforced
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = Autovu_UBC
    MSSQL_ADO_QUERY_FEATURE_TYPES_FOR_MERGE_FILTERS = Yes
    OUTPUT_FEATURES_DISPLAY = Schema and Data Features
    SQL_STATEMENT:
      DECLARE @formatted_timestamp VARCHAR(30);

      SET @formatted_timestamp = DATEADD(SECOND, @Value(latest_timestamp) - 25200, '1970-01-01');

      SELECT *
      FROM dbo.ParkingOccupancies
      WHERE Timestamp > @formatted_timestamp
        AND ZoneId = '@Value(zone_id)';
    RESULT -> CreateSQL_Statements
CreateSQL_Statements: PythonCaller
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              zone_id = feature.getAttribute('ZoneId')
              timezone_id = feature.getAttribute('TimezoneId')
              capacity = feature.getAttribute('Capacity')
              vehicles = feature.getAttribute('Vehicles')
              violations = feature.getAttribute('Violations')
              enforced_violations = feature.getAttribute('ViolationsEnforced')
              timestamp_utc = feature.getAttribute('TimestampUtc')
              timestamp_str = feature.getAttribute('Timestamp')

              # Define the format of the incoming timestamp
              format_str = '%Y-%m-%d %H:%M:%S.%f'

              # Adjust the timestamp string to ensure it matches the expected format
              if len(timestamp_str.split('.')[1]) > 6:
                  timestamp_str = timestamp_str[:21]

              # Convert the timestamp string to a datetime object
              dt = datetime.datetime.strptime(timestamp_str, format_str)

              # Convert the datetime object to a Unix timestamp
              unix_timestamp = int(time.mktime(dt.timetuple()))

              # Add the Unix timestamp as a new attribute
              feature.setAttribute('TimestampUnix', unix_timestamp)

              # Concatenate the attributes into a single string
              feature_string = f"'{zone_id}','{timezone_id}',{capacity},{vehicles},{violations},{enforced_violations},'{timestamp_utc}','{timestamp_str}',{unix_timestamp}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              """This method is called once all the FME Features have been processed
              from input().
              """
              if(self.accumulated_data != "("):
                  self.accumulated_data = self.accumulated_data[:-3]

                  # Create a new output feature with accumulated data
                  out_feature = fmeobjects.FMEFeature()
                  out_feature.setAttribute('accumulated_data', self.accumulated_data.strip())  # Remove trailing space
                  self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewOccupancy_WestParkade [INITIATOR]
WriteNewOccupancy_WestParkade: SQLExecutor
    COMBINE_ATTRS = Result Attributes Only
    COMBINE_GEOM = Initiator Geometry Only
    DATASET = ServerTestDB
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT:
      INSERT INTO WestParkade_Occupancy (
              zone_id,
              TimezoneId,
              Capacity,
              Vehicles,
              Violations,
              ViolationsEnforced,
              TimestampUtc,
              Timestamp,
              TimestampUnix )
      VALUES
          @Value(accumulated_data);
North_Parkade_Latest_Timestamp: SQLExecutor
    COMBINE_ATTRS = Result Attributes Only
    COMBINE_GEOM = Initiator Geometry Only
    DATASET = ServerTestDB
    EXPOSED_ATTRIBUTE_LIST = zone_id,latest_timestamp
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT = SELECT zone_id, MAX(TimestampUnix) AS latest_timestamp FROM Parking.dbo.NorthParkade_Occupancy GROUP BY zone_id
    RESULT -> ReadNewOccupancy_NorthParkade [INITIATOR]
ReadNewOccupancy_NorthParkade: SQLExecutor
    COMBINE_ATTRS = Result Attributes Only
    COMBINE_GEOM = Initiator Geometry Only
    DATASET = Autovu_UBC
    EXPOSED_ATTRIBUTE_LIST = ZoneId,TimestampUtc,Timestamp,TimezoneId,Capacity,Vehicles,Violations,ViolationsEnforced
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = Autovu_UBC
    MSSQL_ADO_QUERY_FEATURE_TYPES_FOR_MERGE_FILTERS = Yes
    OUTPUT_FEATURES_DISPLAY = Schema and Data Features
    SQL_STATEMENT:
      DECLARE @formatted_timestamp VARCHAR(30);

      SET @formatted_timestamp = DATEADD(SECOND, @Value(latest_timestamp) - 25200, '1970-01-01');

      SELECT *
      FROM dbo.ParkingOccupancies
      WHERE Timestamp > @formatted_timestamp
        AND ZoneId = '@Value(zone_id)';
    RESULT -> CreateSQL_Statements_2
CreateSQL_Statements_2: PythonCaller
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              zone_id = feature.getAttribute('ZoneId')
              timezone_id = feature.getAttribute('TimezoneId')
              capacity = feature.getAttribute('Capacity')
              vehicles = feature.getAttribute('Vehicles')
              violations = feature.getAttribute('Violations')
              enforced_violations = feature.getAttribute('ViolationsEnforced')
              timestamp_utc = feature.getAttribute('TimestampUtc')
              timestamp_str = feature.getAttribute('Timestamp')

              # Define the format of the incoming timestamp
              format_str = '%Y-%m-%d %H:%M:%S.%f'

              # Adjust the timestamp string to ensure it matches the expected format
              if len(timestamp_str.split('.')[1]) > 6:
                  timestamp_str = timestamp_str[:21]

              # Convert the timestamp string to a datetime object
              dt = datetime.datetime.strptime(timestamp_str, format_str)

              # Convert the datetime object to a Unix timestamp
              unix_timestamp = int(time.mktime(dt.timetuple()))

              # Add the Unix timestamp as a new attribute
              feature.setAttribute('TimestampUnix', unix_timestamp)

              # Concatenate the attributes into a single string
              feature_string = f"'{zone_id}','{timezone_id}',{capacity},{vehicles},{violations},{enforced_violations},'{timestamp_utc}','{timestamp_str}',{unix_timestamp}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              """This method is called once all the FME Features have been processed
              from input().
              """
              if(self.accumulated_data != "("):
                  self.accumulated_data = self.accumulated_data[:-3]

                  # Create a new output feature with accumulated data
                  out_feature = fmeobjects.FMEFeature()
                  out_feature.setAttribute('accumulated_data', self.accumulated_data.strip())  # Remove trailing space
                  self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewOccupancy_NorthParkade [INITIATOR]
WriteNewOccupancy_NorthParkade: SQLExecutor
    COMBINE_ATTRS = Result Attributes Only
    COMBINE_GEOM = Initiator Geometry Only
    DATASET = ServerTestDB
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT:
      INSERT INTO NorthParkade_Occupancy (
              zone_id,
              TimezoneId,
              Capacity,
              Vehicles,
              Violations,
              ViolationsEnforced,
              TimestampUtc,
              Timestamp,
              TimestampUnix )
      VALUES
          @Value(accumulated_data);
Fraser_Parkade_Latest_Timestamp: SQLExecutor
    COMBINE_ATTRS = Result Attributes Only
    COMBINE_GEOM = Initiator Geometry Only
    DATASET = ServerTestDB
    EXPOSED_ATTRIBUTE_LIST = zone_id,latest_timestamp
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT = SELECT zone_id, MAX(TimestampUnix) AS latest_timestamp FROM Parking.dbo.FraserParkade_Occupancy GROUP BY zone_id
    RESULT -> ReadNewOccupancy_FraserParkade [INITIATOR]
ReadNewOccupancy_FraserParkade: SQLExecutor
    COMBINE_ATTRS = Result Attributes Only
    COMBINE_GEOM = Initiator Geometry Only
    DATASET = Autovu_UBC
    EXPOSED_ATTRIBUTE_LIST = ZoneId,TimestampUtc,Timestamp,TimezoneId,Capacity,Vehicles,Violations,ViolationsEnforced
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = Autovu_UBC
    MSSQL_ADO_QUERY_FEATURE_TYPES_FOR_MERGE_FILTERS = Yes
    OUTPUT_FEATURES_DISPLAY = Schema and Data Features
    SQL_STATEMENT:
      DECLARE @formatted_timestamp VARCHAR(30);

      SET @formatted_timestamp = DATEADD(SECOND, @Value(latest_timestamp) - 25200, '1970-01-01');

      SELECT *
      FROM dbo.ParkingOccupancies
      WHERE Timestamp > @formatted_timestamp
        AND ZoneId = '@Value(zone_id)';
    RESULT -> CreateSQL_Statements_3
CreateSQL_Statements_3: PythonCaller
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              zone_id = feature.getAttribute('ZoneId')
              timezone_id = feature.getAttribute('TimezoneId')
              capacity = feature.getAttribute('Capacity')
              vehicles = feature.getAttribute('Vehicles')
              violations = feature.getAttribute('Violations')
              enforced_violations = feature.getAttribute('ViolationsEnforced')
              timestamp_utc = feature.getAttribute('TimestampUtc')
              timestamp_str = feature.getAttribute('Timestamp')

              # Define the format of the incoming timestamp
              format_str = '%Y-%m-%d %H:%M:%S.%f'

              # Adjust the timestamp string to ensure it matches the expected format
              if len(timestamp_str.split('.')[1]) > 6:
                  timestamp_str = timestamp_str[:21]

              # Convert the timestamp string to a datetime object
              dt = datetime.datetime.strptime(timestamp_str, format_str)

              # Convert the datetime object to a Unix timestamp
              unix_timestamp = int(time.mktime(dt.timetuple()))

              # Add the Unix timestamp as a new attribute
              feature.setAttribute('TimestampUnix', unix_timestamp)

              # Concatenate the attributes into a single string
              feature_string = f"'{zone_id}','{timezone_id}',{capacity},{vehicles},{violations},{enforced_violations},'{timestamp_utc}','{timestamp_str}',{unix_timestamp}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              """This method is called once all the FME Features have been processed
              from input().
              """
              if(self.accumulated_data != "("):
                  self.accumulated_data = self.accumulated_data[:-3]

                  # Create a new output feature with accumulated data
                  out_feature = fmeobjects.FMEFeature()
                  out_feature.setAttribute('accumulated_data', self.accumulated_data.strip())  # Remove trailing space
                  self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewOccupancy_FraserParkade [INITIATOR]
WriteNewOccupancy_FraserParkade: SQLExecutor
    COMBINE_ATTRS = Result Attributes Only
    COMBINE_GEOM = Initiator Geometry Only
    DATASET = ServerTestDB
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT:
      INSERT INTO FraserParkade_Occupancy (
              zone_id,
              TimezoneId,
              Capacity,
              Vehicles,
              Violations,
              ViolationsEnforced,
              TimestampUtc,
              Timestamp,
              TimestampUnix )
      VALUES
          @Value(accumulated_data);
Thunderbird_Parkade_Latest_Timestamp: SQLExecutor
    COMBINE_ATTRS = Result Attributes Only
    COMBINE_GEOM = Initiator Geometry Only
    DATASET = ServerTestDB
    EXPOSED_ATTRIBUTE_LIST = zone_id,latest_timestamp
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT = SELECT zone_id, MAX(TimestampUnix) AS latest_timestamp FROM Parking.dbo.ThunderbirdParkade_Occupancy GROUP BY zone_id
    RESULT -> ReadNewOccupancy_ThunderbirdParkade [INITIATOR]
ReadNewOccupancy_ThunderbirdParkade: SQLExecutor
    COMBINE_ATTRS = Result Attributes Only
    COMBINE_GEOM = Initiator Geometry Only
    DATASET = Autovu_UBC
    EXPOSED_ATTRIBUTE_LIST = ZoneId,TimestampUtc,Timestamp,TimezoneId,Capacity,Vehicles,Violations,ViolationsEnforced
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = Autovu_UBC
    MSSQL_ADO_QUERY_FEATURE_TYPES_FOR_MERGE_FILTERS = Yes
    OUTPUT_FEATURES_DISPLAY = Schema and Data Features
    SQL_STATEMENT:
      DECLARE @formatted_timestamp VARCHAR(30);

      SET @formatted_timestamp = DATEADD(SECOND, @Value(latest_timestamp) - 25200, '1970-01-01');

      SELECT *
      FROM dbo.ParkingOccupancies
      WHERE Timestamp > @formatted_timestamp
        AND ZoneId = '@Value(zone_id)';
    RESULT -> CreateSQL_Statements_4
CreateSQL_Statements_4: PythonCaller
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              zone_id = feature.getAttribute('ZoneId')
              timezone_id = feature.getAttribute('TimezoneId')
              capacity = feature.getAttribute('Capacity')
              vehicles = feature.getAttribute('Vehicles')
              violations = feature.getAttribute('Violations')
              enforced_violations = feature.getAttribute('ViolationsEnforced')
              timestamp_utc = feature.getAttribute('TimestampUtc')
              timestamp_str = feature.getAttribute('Timestamp')

              # Define the format of the incoming timestamp
              format_str = '%Y-%m-%d %H:%M:%S.%f'

              # Adjust the timestamp string to ensure it matches the expected format
              if len(timestamp_str.split('.')[1]) > 6:
                  timestamp_str = timestamp_str[:21]

              # Convert the timestamp string to a datetime object
              dt = datetime.datetime.strptime(timestamp_str, format_str)

              # Convert the datetime object to a Unix timestamp
              unix_timestamp = int(time.mktime(dt.timetuple()))

              # Add the Unix timestamp as a new attribute
              feature.setAttribute('TimestampUnix', unix_timestamp)

              # Concatenate the attributes into a single string
              feature_string = f"'{zone_id}','{timezone_id}',{capacity},{vehicles},{violations},{enforced_violations},'{timestamp_utc}','{timestamp_str}',{unix_timestamp}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              """This method is called once all the FME Features have been processed
              from input().
              """
              if(self.accumulated_data != "("):
                  self.accumulated_data = self.accumulated_data[:-3]

                  # Create a new output feature with accumulated data
                  out_feature = fmeobjects.FMEFeature()
                  out_feature.setAttribute('accumulated_data', self.accumulated_data.strip())  # Remove trailing space
                  self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewOccupancy_ThunderbirdParkade [INITIATOR]
WriteNewOccupancy_ThunderbirdParkade: SQLExecutor
    COMBINE_ATTRS = Result Attributes Only
    COMBINE_GEOM = Initiator Geometry Only
    DATASET = ServerTestDB
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT:
      INSERT INTO ThunderbirdParkade_Occupancy (
              zone_id,
              TimezoneId,
              Capacity,
              Vehicles,
              Violations,
              ViolationsEnforced,
              TimestampUtc,
              Timestamp,
              TimestampUnix )
      VALUES
          @Value(accumulated_data);
RoseGarden_Parkade_Latest_Timestamp: SQLExecutor
    COMBINE_ATTRS = Result Attributes Only
    COMBINE_GEOM = Initiator Geometry Only
    DATASET = ServerTestDB
    EXPOSED_ATTRIBUTE_LIST = zone_id,latest_timestamp
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT = SELECT zone_id, MAX(TimestampUnix) AS latest_timestamp FROM Parking.dbo.RoseGardenParkade_Occupancy GROUP BY zone_id
    RESULT -> ReadNewOccupancy_RoseGardenParkade [INITIATOR]
ReadNewOccupancy_RoseGardenParkade: SQLExecutor
    COMBINE_ATTRS = Result Attributes Only
    COMBINE_GEOM = Initiator Geometry Only
    DATASET = Autovu_UBC
    EXPOSED_ATTRIBUTE_LIST = ZoneId,TimestampUtc,Timestamp,TimezoneId,Capacity,Vehicles,Violations,ViolationsEnforced
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = Autovu_UBC
    MSSQL_ADO_QUERY_FEATURE_TYPES_FOR_MERGE_FILTERS = Yes
    OUTPUT_FEATURES_DISPLAY = Schema and Data Features
    SQL_STATEMENT:
      DECLARE @formatted_timestamp VARCHAR(30);

      SET @formatted_timestamp = DATEADD(SECOND, @Value(latest_timestamp) - 25200, '1970-01-01');

      SELECT *
      FROM dbo.ParkingOccupancies
      WHERE Timestamp > @formatted_timestamp
        AND ZoneId = '@Value(zone_id)';
    RESULT -> CreateSQL_Statements_5
CreateSQL_Statements_5: PythonCaller
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              zone_id = feature.getAttribute('ZoneId')
              timezone_id = feature.getAttribute('TimezoneId')
              capacity = feature.getAttribute('Capacity')
              vehicles = feature.getAttribute('Vehicles')
              violations = feature.getAttribute('Violations')
              enforced_violations = feature.getAttribute('ViolationsEnforced')
              timestamp_utc = feature.getAttribute('TimestampUtc')
              timestamp_str = feature.getAttribute('Timestamp')

              # Define the format of the incoming timestamp
              format_str = '%Y-%m-%d %H:%M:%S.%f'

              # Adjust the timestamp string to ensure it matches the expected format
              if len(timestamp_str.split('.')[1]) > 6:
                  timestamp_str = timestamp_str[:21]

              # Convert the timestamp string to a datetime object
              dt = datetime.datetime.strptime(timestamp_str, format_str)

              # Convert the datetime object to a Unix timestamp
              unix_timestamp = int(time.mktime(dt.timetuple()))

              # Add the Unix timestamp as a new attribute
              feature.setAttribute('TimestampUnix', unix_timestamp)

              # Concatenate the attributes into a single string
              feature_string = f"'{zone_id}','{timezone_id}',{capacity},{vehicles},{violations},{enforced_violations},'{timestamp_utc}','{timestamp_str}',{unix_timestamp}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              """This method is called once all the FME Features have been processed
              from input().
              """
              if(self.accumulated_data != "("):
                  self.accumulated_data = self.accumulated_data[:-3]

                  # Create a new output feature with accumulated data
                  out_feature = fmeobjects.FMEFeature()
                  out_feature.setAttribute('accumulated_data', self.accumulated_data.strip())  # Remove trailing space
                  self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewOccupancy_RoseGardenParkade [INITIATOR]
WriteNewOccupancy_RoseGardenParkade: SQLExecutor
    COMBINE_ATTRS = Result Attributes Only
    COMBINE_GEOM = Initiator Geometry Only
    DATASET = ServerTestDB
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT:
      INSERT INTO RoseGardenParkade_Occupancy (
              zone_id,
              TimezoneId,
              Capacity,
              Vehicles,
              Violations,
              ViolationsEnforced,
              TimestampUtc,
              Timestamp,
              TimestampUnix )
      VALUES
          @Value(accumulated_data);
HealthSciences_Parkade_Latest_Timestamp: SQLExecutor
    COMBINE_ATTRS = Result Attributes Only
    COMBINE_GEOM = Initiator Geometry Only
    DATASET = ServerTestDB
    EXPOSED_ATTRIBUTE_LIST = zone_id,latest_timestamp
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT = SELECT zone_id, MAX(TimestampUnix) AS latest_timestamp FROM Parking.dbo.HealthSciencesParkade_Occupancy GROUP BY zone_id
    RESULT -> ReadNewOccupancy_HealthSciencesParkade [INITIATOR]
ReadNewOccupancy_HealthSciencesParkade: SQLExecutor
    COMBINE_ATTRS = Result Attributes Only
    COMBINE_GEOM = Initiator Geometry Only
    DATASET = Autovu_UBC
    EXPOSED_ATTRIBUTE_LIST = ZoneId,TimestampUtc,Timestamp,TimezoneId,Capacity,Vehicles,Violations,ViolationsEnforced
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = Autovu_UBC
    MSSQL_ADO_QUERY_FEATURE_TYPES_FOR_MERGE_FILTERS = Yes
    OUTPUT_FEATURES_DISPLAY = Schema and Data Features
    SQL_STATEMENT:
      DECLARE @formatted_timestamp VARCHAR(30);

      SET @formatted_timestamp = DATEADD(SECOND, @Value(latest_timestamp) - 25200, '1970-01-01');

      SELECT *
      FROM dbo.ParkingOccupancies
      WHERE Timestamp > @formatted_timestamp
        AND ZoneId = '@Value(zone_id)';
    RESULT -> CreateSQL_Statements_6
CreateSQL_Statements_6: PythonCaller
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              zone_id = feature.getAttribute('ZoneId')
              timezone_id = feature.getAttribute('TimezoneId')
              capacity = feature.getAttribute('Capacity')
              vehicles = feature.getAttribute('Vehicles')
              violations = feature.getAttribute('Violations')
              enforced_violations = feature.getAttribute('ViolationsEnforced')
              timestamp_utc = feature.getAttribute('TimestampUtc')
              timestamp_str = feature.getAttribute('Timestamp')

              # Define the format of the incoming timestamp
              format_str = '%Y-%m-%d %H:%M:%S.%f'

              # Adjust the timestamp string to ensure it matches the expected format
              if len(timestamp_str.split('.')[1]) > 6:
                  timestamp_str = timestamp_str[:21]

              # Convert the timestamp string to a datetime object
              dt = datetime.datetime.strptime(timestamp_str, format_str)

              # Convert the datetime object to a Unix timestamp
              unix_timestamp = int(time.mktime(dt.timetuple()))

              # Add the Unix timestamp as a new attribute
              feature.setAttribute('TimestampUnix', unix_timestamp)

              # Concatenate the attributes into a single string
              feature_string = f"'{zone_id}','{timezone_id}',{capacity},{vehicles},{violations},{enforced_violations},'{timestamp_utc}','{timestamp_str}',{unix_timestamp}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              """This method is called once all the FME Features have been processed
              from input().
              """
              if(self.accumulated_data != "("):
                  self.accumulated_data = self.accumulated_data[:-3]

                  # Create a new output feature with accumulated data
                  out_feature = fmeobjects.FMEFeature()
                  out_feature.setAttribute('accumulated_data', self.accumulated_data.strip())  # Remove trailing space
                  self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewOccupancy_HealthSciencesParkade [INITIATOR]
WriteNewOccupancy_HealthSciencesParkade: SQLExecutor
    COMBINE_ATTRS = Result Attributes Only
    COMBINE_GEOM = Initiator Geometry Only
    DATASET = ServerTestDB
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT:
      INSERT INTO HealthSciencesParkade_Occupancy (
              zone_id,
              TimezoneId,
              Capacity,
              Vehicles,
              Violations,
              ViolationsEnforced,
              TimestampUtc,
              Timestamp,
              TimestampUnix )
      VALUES
          @Value(accumulated_data);
UnivWstBlvd_Parkade_Latest_Timestamp: SQLExecutor
    COMBINE_ATTRS = Result Attributes Only
    COMBINE_GEOM = Initiator Geometry Only
    DATASET = ServerTestDB
    EXPOSED_ATTRIBUTE_LIST = zone_id,latest_timestamp
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT = SELECT zone_id, MAX(TimestampUnix) AS latest_timestamp FROM Parking.dbo.UnivWstBlvdParkade_Occupancy GROUP BY zone_id
    RESULT -> ReadNewOccupancy_UnivWstBlvdParkade [INITIATOR]
ReadNewOccupancy_UnivWstBlvdParkade: SQLExecutor
    COMBINE_ATTRS = Result Attributes Only
    COMBINE_GEOM = Initiator Geometry Only
    DATASET = Autovu_UBC
    EXPOSED_ATTRIBUTE_LIST = ZoneId,TimestampUtc,Timestamp,TimezoneId,Capacity,Vehicles,Violations,ViolationsEnforced
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = Autovu_UBC
    MSSQL_ADO_QUERY_FEATURE_TYPES_FOR_MERGE_FILTERS = Yes
    OUTPUT_FEATURES_DISPLAY = Schema and Data Features
    SQL_STATEMENT:
      DECLARE @formatted_timestamp VARCHAR(30);

      SET @formatted_timestamp = DATEADD(SECOND, @Value(latest_timestamp) - 25200, '1970-01-01');

      SELECT *
      FROM dbo.ParkingOccupancies
      WHERE Timestamp > @formatted_timestamp
        AND ZoneId = '@Value(zone_id)';
    RESULT -> CreateSQL_Statements_7
CreateSQL_Statements_7: PythonCaller
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              zone_id = feature.getAttribute('ZoneId')
              timezone_id = feature.getAttribute('TimezoneId')
              capacity = feature.getAttribute('Capacity')
              vehicles = feature.getAttribute('Vehicles')
              violations = feature.getAttribute('Violations')
              enforced_violations = feature.getAttribute('ViolationsEnforced')
              timestamp_utc = feature.getAttribute('TimestampUtc')
              timestamp_str = feature.getAttribute('Timestamp')

              # Define the format of the incoming timestamp
              format_str = '%Y-%m-%d %H:%M:%S.%f'

              # Adjust the timestamp string to ensure it matches the expected format
              if len(timestamp_str.split('.')[1]) > 6:
                  timestamp_str = timestamp_str[:21]

              # Convert the timestamp string to a datetime object
              dt = datetime.datetime.strptime(timestamp_str, format_str)

              # Convert the datetime object to a Unix timestamp
              unix_timestamp = int(time.mktime(dt.timetuple()))

              # Add the Unix timestamp as a new attribute
              feature.setAttribute('TimestampUnix', unix_timestamp)

              # Concatenate the attributes into a single string
              feature_string = f"'{zone_id}','{timezone_id}',{capacity},{vehicles},{violations},{enforced_violations},'{timestamp_utc}','{timestamp_str}',{unix_timestamp}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              """This method is called once all the FME Features have been processed
              from input().
              """
              if(self.accumulated_data != "("):
                  self.accumulated_data = self.accumulated_data[:-3]

                  # Create a new output feature with accumulated data
                  out_feature = fmeobjects.FMEFeature()
                  out_feature.setAttribute('accumulated_data', self.accumulated_data.strip())  # Remove trailing space
                  self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewOccupancy_UnivWstBlvdParkade [INITIATOR]
WriteNewOccupancy_UnivWstBlvdParkade: SQLExecutor
    COMBINE_ATTRS = Result Attributes Only
    COMBINE_GEOM = Initiator Geometry Only
    DATASET = ServerTestDB
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT:
      INSERT INTO UnivWstBlvdParkade_Occupancy (
              zone_id,
              TimezoneId,
              Capacity,
              Vehicles,
              Violations,
              ViolationsEnforced,
              TimestampUtc,
              Timestamp,
              TimestampUnix )
      VALUES
          @Value(accumulated_data);
