FME workspace x11_management_table.fmw

Parameters:
- DestDataset_CSV2 = C:\!Capstone\repo\TL16\data-consolidation   # Destination CSV (Comma Separated Value) Folder

Writers:
- CSV2_1: CSV2 to $(DestDataset_CSV2)

Creator
    GEOMTYPE = Geometry Object
    NUM = 1
    CREATED -> X11_UBC_zone
X11_UBC_zone: HTTPCaller
    CONNECTION_TIMEOUT_LENGTH = 60
    CUSTOM_HEADERS = Accept;application/json Authorization;Bearer eyJ0eXAiOiJKV1QiLCJhbGciOiJSUzI1NiJ9.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.LGrwl-yYHRViX8wTCPswtk1rGeb7VtCBMNqS78kj6vDJYY66tSnD0NW36eOHK5TL-1Mmmp9SGQDZgATSZSEj0hm2d8dZ9EXPab3jufUySlb4lLgauT8qNxQnoIjEGTSXsdHQu2mbd_97BtjF_yPDDW1Gsp01SBuLbI0uQoRkRKvUEuabFghzpV_01XmL7Lw8Fl3-T1lFI9cUfzGraKRfiePYrhM-z55xv9EfTfZSb5lFjgo8QSPNjCA0D5DJ00da67KWYQUZ4oubolr_ydR1dAbbpC9Whd3Twe--JRenHyxAwgpM0sBhkj7MZcaZ19Tvf1N52lgxwl-ocuWbdSoK6T4IkUdeM7wUARfo47GywiOMUwqMdSUt82bMk-AieGsysxZyWV_gAVx6ACxofx4UgMGTZC4PKql6sSi7onjc7Pt_vIb7Vj-oU2KtqPjCHCKlWOkgNFj5A4lCDMcNzFExSI89nWsvWqzhv7132yrLDWOpRBVP5o7rjXZ3jyGw06J6jCVRYwpNPlNs59qbP9TRb0IqQFg8FLAzMUt_Bx6EEFFmbUb3XzDtxdrfdfwel5ZrWtoE0QMGfObe5NxxYYHQDtpVpakBUWYkmNrbNUgvgxuJupe3QnM29s_YP6q-1XTAw1eoz9009a115iBuRUOIxjJs7iC8eBhxUWijuHD2Ksk
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://app.eleven-x.com/api/v2/info/parking/zones/78?dynamic_zones_excluded=false&direct_only=false
    TRANSFER_TIMEOUT_LENGTH = 90
    USE_COOKIES = No
    VERIFY_SSL_CERTIFICATES = Yes
    -> SubZone_Info_Extractor
SubZone_Info_Extractor: PythonCaller
    HIDE_ATTRIBUTES = _http_status_code _response_body _creation_instance
    NEW_ATTRIBUTES = zone_display_name zone_id
    PYTHONSOURCE:
      import fme
      import fmeobjects
      import json


      class FeatureProcessor(object):
          """Template Class Interface:
          When using this class, make sure its name is set as the value of the 'Class
          to Process Features' transformer parameter.
          """



          def __init__(self):
              """Base constructor for class members."""
              self.feature_list = []
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              response = json.loads(feature.getAttribute('_response_body'))
              sub_zones = response.get("infoParkingZone", {}).get("sub_zones", [])

              # Write the subzones data
              for subzone in sub_zones:
                  row = [subzone['zone_id'], subzone['display_name']]
                  # print("zone_id: " + str(subzone['zone_id']) + "\ndispaly name: " + str(subzone['display_name']) + "\n")
                  newFeature = fmeobjects.FMEFeature()
                  newFeature.setAttribute('zone_id', str(subzone['zone_id']))
                  newFeature.setAttribute('zone_display_name', str(subzone['display_name']))
                  self.feature_list.append(newFeature)


          def close(self):
              """This method is called once all the FME Features have been processed
              from input().
              """
              for feature in self.feature_list:
                  self.pyoutput(feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> X11_subzone_info
X11_subzone_info: HTTPCaller
    CONNECTION_TIMEOUT_LENGTH = 60
    CUSTOM_HEADERS = Accept;application/json Authorization;Bearer eyJ0eXAiOiJKV1QiLCJhbGciOiJSUzI1NiJ9.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.LGrwl-yYHRViX8wTCPswtk1rGeb7VtCBMNqS78kj6vDJYY66tSnD0NW36eOHK5TL-1Mmmp9SGQDZgATSZSEj0hm2d8dZ9EXPab3jufUySlb4lLgauT8qNxQnoIjEGTSXsdHQu2mbd_97BtjF_yPDDW1Gsp01SBuLbI0uQoRkRKvUEuabFghzpV_01XmL7Lw8Fl3-T1lFI9cUfzGraKRfiePYrhM-z55xv9EfTfZSb5lFjgo8QSPNjCA0D5DJ00da67KWYQUZ4oubolr_ydR1dAbbpC9Whd3Twe--JRenHyxAwgpM0sBhkj7MZcaZ19Tvf1N52lgxwl-ocuWbdSoK6T4IkUdeM7wUARfo47GywiOMUwqMdSUt82bMk-AieGsysxZyWV_gAVx6ACxofx4UgMGTZC4PKql6sSi7onjc7Pt_vIb7Vj-oU2KtqPjCHCKlWOkgNFj5A4lCDMcNzFExSI89nWsvWqzhv7132yrLDWOpRBVP5o7rjXZ3jyGw06J6jCVRYwpNPlNs59qbP9TRb0IqQFg8FLAzMUt_Bx6EEFFmbUb3XzDtxdrfdfwel5ZrWtoE0QMGfObe5NxxYYHQDtpVpakBUWYkmNrbNUgvgxuJupe3QnM29s_YP6q-1XTAw1eoz9009a115iBuRUOIxjJs7iC8eBhxUWijuHD2Ksk
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://app.eleven-x.com/api/v2/info/parking/zones/@Value(zone_id)?dynamic_zones_excluded=false&direct_only=false
    TRANSFER_TIMEOUT_LENGTH = 90
    USE_COOKIES = No
    VERIFY_SSL_CERTIFICATES = Yes
    -> Stall_List_Extractor
Stall_List_Extractor: PythonCaller
    HIDE_ATTRIBUTES = _http_status_code _response_body
    NEW_ATTRIBUTES = stall_id stall_display_name zone_id zone_display_name
    PYTHONSOURCE:
      import fme
      import fmeobjects


      class FeatureProcessor(object):

          def __init__(self):
              self.feature_list = []
              pass

          def input(self, feature):
              zone_id = feature.getAttribute('zone_id')
              zone_display_name = feature.getAttribute('zone_display_name')

              response = json.loads(feature.getAttribute('_response_body'))
              stalls = response.get("infoParkingZone", {}).get("stalls", [])

              # Write the subzones data
              for stall in stalls:
                  newFeature = fmeobjects.FMEFeature()
                  newFeature.setAttribute('stall_id', str(stall['stall_id']))
                  newFeature.setAttribute('stall_display_name', str(stall['display_name']))
                  newFeature.setAttribute('zone_id', str(zone_id))
                  newFeature.setAttribute('zone_display_name', zone_display_name)
                  self.feature_list.append(newFeature)

          def close(self):
              for feature in self.feature_list:
                  self.pyoutput(feature)
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> AddStallnfo
AddStallnfo: HTTPCaller
    CONNECTION_TIMEOUT_LENGTH = 60
    CUSTOM_HEADERS = Authorization;Bearer eyJ0eXAiOiJKV1QiLCJhbGciOiJSUzI1NiJ9.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.LGrwl-yYHRViX8wTCPswtk1rGeb7VtCBMNqS78kj6vDJYY66tSnD0NW36eOHK5TL-1Mmmp9SGQDZgATSZSEj0hm2d8dZ9EXPab3jufUySlb4lLgauT8qNxQnoIjEGTSXsdHQu2mbd_97BtjF_yPDDW1Gsp01SBuLbI0uQoRkRKvUEuabFghzpV_01XmL7Lw8Fl3-T1lFI9cUfzGraKRfiePYrhM-z55xv9EfTfZSb5lFjgo8QSPNjCA0D5DJ00da67KWYQUZ4oubolr_ydR1dAbbpC9Whd3Twe--JRenHyxAwgpM0sBhkj7MZcaZ19Tvf1N52lgxwl-ocuWbdSoK6T4IkUdeM7wUARfo47GywiOMUwqMdSUt82bMk-AieGsysxZyWV_gAVx6ACxofx4UgMGTZC4PKql6sSi7onjc7Pt_vIb7Vj-oU2KtqPjCHCKlWOkgNFj5A4lCDMcNzFExSI89nWsvWqzhv7132yrLDWOpRBVP5o7rjXZ3jyGw06J6jCVRYwpNPlNs59qbP9TRb0IqQFg8FLAzMUt_Bx6EEFFmbUb3XzDtxdrfdfwel5ZrWtoE0QMGfObe5NxxYYHQDtpVpakBUWYkmNrbNUgvgxuJupe3QnM29s_YP6q-1XTAw1eoz9009a115iBuRUOIxjJs7iC8eBhxUWijuHD2Ksk Accept;application/json
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    RETRY_FAILED_TRANSFERS = CONNECTION 429 500 501 502 503 504 505 506 507 508 509 510 511
    RETRY_INITIAL_BACKOFF = 5000
    RETRY_MAX_RETRIES = 10
    SPLIT_MULTIPART_DOWNLOADS = NO
    STATUS_CODE_ATTR = _http_status_code
    TARGET_ATTR = _response_body
    TARGET_ATTR_ENCODING = auto-detect
    TARGET_URL = https://app.eleven-x.com/api/v2/info/parking/stalls/@Value(stall_id)
    TRANSFER_TIMEOUT_LENGTH = 90
    USE_COOKIES = No
    VERIFY_SSL_CERTIFICATES = Yes
    -> AppendStallInfo
AppendStallInfo: PythonCaller
    HIDE_ATTRIBUTES = _http_status_code _response_body
    NEW_ATTRIBUTES = stall_id stall_display_name zone_id zone_display_name longitude latitude device_eui linked_date
    PYTHONSOURCE:
      import fme
      import fmeobjects
      import json

      class FeatureProcessor(object):

          def __init__(self):
              pass

          def input(self, feature):
              response = json.loads(feature.getAttribute('_response_body'))
              stall_data = response.get("infoParkingStall", {},)

              # Update location fields to be part of top level dictionary
              if 'location' in stall_data:
                  temp_location = stall_data['location'].copy()
                  feature.setAttribute('longitude', str(temp_location['longitude']))
                  feature.setAttribute('latitude', str(temp_location['latitude']))

              # Update device fields to be part of top level dictionary
              if 'linked_device' in stall_data:
                  temp_device = stall_data['linked_device'].copy()
                  feature.setAttribute('device_eui', str(temp_device['device_eui']))
                  feature.setAttribute('linked_date', str(temp_device['linked_date']))

              self.pyoutput(feature)

          def close(self):
              pass

          def process_group(self):
              pass

          def has_support_for(self, support_type):
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> SQLExecutor [INITIATOR]
SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      -- Insert a new row into the table using the declared variables
      INSERT INTO dbo.x11_management (
          stall_id,
          stall_display_name,
          zone_id,
          zone_display_name,
          device_eui,
          linked_date,
          longitude,
          latitude
      ) VALUES (
          @Value(stall_id),
          '@Value(stall_display_name)',
          @Value(zone_id),
          '@Value(zone_display_name)',
          '@Value(device_eui)',
          '@Value(linked_date)',
          @Value(longitude),
          @Value(latitude)
      );
