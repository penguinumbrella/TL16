FME workspace parking_stats_daily.fmw

Creator
    GEOMTYPE = Geometry Object
    NUM = 1
    CREATED -> GetLatestDayStatsWestParkade [INITIATOR]
    CREATED -> GetLatestDayStatsUnivWstBlvd [INITIATOR]
    CREATED -> GetLatestDayStatsThunderbird [INITIATOR]
    CREATED -> GetLatestDayStatsRoseGarden [INITIATOR]
    CREATED -> GetLatestDayStatsNorth [INITIATOR]
    CREATED -> GetLatestDayStatsHealthSciences [INITIATOR]
    CREATED -> GetLatestDayStatsFraser [INITIATOR]
GetLatestDayStatsWestParkade: SQLExecutor
    COMBINE_ATTRS = Result Attributes Only
    COMBINE_GEOM = Initiator Geometry Only
    DATASET = AWS_UBCParking
    EXPOSED_ATTRIBUTE_LIST = date
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      SELECT TOP 1 *
      FROM [Parking].[dbo].[Daily_Occupancy_Stats]
      WHERE zone_id = 'E10D7DB4-C792-42AC-BAE8-969FA63F198D'
      ORDER BY date DESC;
    RESULT -> ConvertDayToUnix
ConvertDayToUnix: PythonCaller
    NEW_ATTRIBUTES = date day_unixtimestamp
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              pass

          def input(self, feature):

              # Convert the date string to a datetime object
              date_time = datetime.datetime.strptime(feature.getAttribute('date'), '%Y%m%d')

              # Convert the datetime object to a UNIX timestamp
              unix_timestamp = int(date_time.timestamp())

              print(f"Date: {feature.getAttribute('date')} -> UNIX Timestamp: {unix_timestamp}")

              feature.setAttribute('day_unixtimestamp', unix_timestamp)

              self.pyoutput(feature)

          def close(self):
              # Dictionary to store timestamps and their corresponding indices

              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> GetAllDataFromLatestDayWestParkade [INITIATOR]
GetAllDataFromLatestDayWestParkade: SQLExecutor
    COMBINE_ATTRS = Result Attributes Only
    COMBINE_GEOM = Initiator Geometry Only
    DATASET = AWS_UBCParking
    EXPOSED_ATTRIBUTE_LIST = zone_id,TimezoneId,Capacity,Vehicles,Violations,ViolationsEnforced,TimestampUTC,Timestamp,TimestampUnix
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 60
    OUTPUT_FEATURES_DISPLAY = Schema and Data Features
    SQL_STATEMENT:
      SELECT DISTINCT *
      FROM [dbo].[WestParkade_Occupancy]
      WHERE TimestampUnix > @Value(day_unixtimestamp)
    RESULT -> AddDayHour
AddDayHour: PythonCaller
    HIDE_ATTRIBUTES = Timestamp TimestampUnix TimestampUTC TimezoneId Violations ViolationsEnforced zone_id
    NEW_ATTRIBUTES = Date hour_minute Vehicles Capacity
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.data = []
              pass

          def input(self, feature):
              # Convert UNIX timestamp to a datetime object
              date_time = datetime.datetime.fromtimestamp(feature.getAttribute('TimestampUnix'))

              # Format the datetime object to a string in yyyy-mm-dd format
              formatted_date = date_time.strftime('%Y-%m-%d')

              # Get the hour and minute from the datetime object
              hour_minute = date_time.strftime('%H:%M')

              feature.setAttribute('Date', formatted_date)
              feature.setAttribute('hour_minute', hour_minute)

              self.data.append(feature)
              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CalculateStatsPerDay
CalculateStatsPerDay: PythonCaller
    GROUP_BY = Date
    HIDE_ATTRIBUTES = Date hour_minute Vehicles
    NEW_ATTRIBUTES = Capacity average_occupancy peak_occupancy peak_occupancy_time date
    PYTHONSOURCE:
      import fme
      import fmeobjects
      import datetime

      def datetime_to_unixtimestamp(date_str, time_str):
          try:
              # Parse date and time strings
              date_obj = datetime.datetime.strptime(date_str, "%Y-%m-%d").date()
              time_obj = datetime.datetime.strptime(time_str, "%H:%M").time()

              # Combine date and time
              datetime_combined = datetime.datetime.combine(date_obj, time_obj)

              # Convert to Unix timestamp
              unix_timestamp = int(datetime_combined.timestamp())
              return unix_timestamp
          except ValueError:
              return None


      class FeatureProcessor(object):
          """Template Class Interface:
          When using this class, make sure its name is set as the value of the 'Class
          to Process Features' transformer parameter.
          """
          def __init__(self):
              """Base constructor for class members."""
              self.norm_occ = 0
              self.n = 0
              self.average_occupancy = 0
              self.peak_occupancy = 0
              self.peak_occupancy_time = 0
              self_capacity = 0
              self.date = ""
              self.today = datetime.date.today()
              pass

          def input(self, feature):
              self.date = feature.getAttribute('Date')

              if datetime.datetime.strptime(self.date, "%Y-%m-%d").date() != self.today:
                  self.norm_occ += feature.getAttribute('Vehicles')
                  self.n += 1
                  self.capacity = feature.getAttribute('Capacity')
                  if(self.peak_occupancy < feature.getAttribute('Vehicles')):
                      self.peak_occupancy = feature.getAttribute('Vehicles')
                      self.peak_occupancy_time = feature.getAttribute('hour_minute')
                  """This method is called for each FME Feature entering the
                  PythonCaller. If knowledge of all input Features is not required for
                  processing, then the processed Feature can be emitted from this method
                  through self.pyoutput(). Otherwise, the input FME Feature should be
                  cached to a list class member and processed in process_group() when
                  'Group by' attributes(s) are specified, or the close() method.

                  :param fmeobjects.FMEFeature feature: FME Feature entering the
                      transformer.
                  """

          def close(self):
              """This method is called once all the FME Features have been processed
              from input().
              """

              pass

          def process_group(self):
              if datetime.datetime.strptime(self.date, "%Y-%m-%d").date() != self.today:
                  self.average_occupancy = self.norm_occ / self.n

                  out_feature = fmeobjects.FMEFeature()
                  out_feature.setAttribute('average_occupancy', int(self.average_occupancy))
                  out_feature.setAttribute('peak_occupancy', self.peak_occupancy)
                  out_feature.setAttribute('peak_occupancy_time', datetime_to_unixtimestamp(str(self.date), str(self.peak_occupancy_time)))
                  out_feature.setAttribute('Capacity', self.capacity)
                  out_feature.setAttribute('date', self.date)
                  self.pyoutput(out_feature)
                  self.peak_occupancy = 0
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CreateSQL_WestParkade
CreateSQL_WestParkade: PythonCaller
    HIDE_ATTRIBUTES = average_occupancy Capacity date peak_occupancy peak_occupancy_time
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              average_occupancy = feature.getAttribute('average_occupancy')
              capacity = feature.getAttribute('Capacity')
              date = feature.getAttribute('date')
              peak_occupancy = feature.getAttribute('peak_occupancy')
              peak_occupancy_time = feature.getAttribute('peak_occupancy_time')
              zone_id = 'E10D7DB4-C792-42AC-BAE8-969FA63F198D'


              # Concatenate the attributes into a single string
              feature_string = f"'{date}','{zone_id}',{average_occupancy},{peak_occupancy},{peak_occupancy_time},{capacity}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              if(self.accumulated_data):
                  """This method is called once all the FME Features have been processed
                  from input().
                  """
                  self.accumulated_data = self.accumulated_data[:-3]

                  # Create a new output feature with accumulated data
                  out_feature = fmeobjects.FMEFeature()
                  out_feature.setAttribute('accumulated_data', self.accumulated_data.strip())  # Remove trailing space
                  self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewStats_WestParkade [INITIATOR]
WriteNewStats_WestParkade: SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      ;WITH UniqueSource AS (
          SELECT   date,
                   zone_id,
                   average_occupancy,
                   peak_occupancy,
                   peak_occupancy_time,
                   Capacity
          FROM (
              SELECT
                   date,
                   zone_id,
                   average_occupancy,
                   peak_occupancy,
                   peak_occupancy_time,
                   Capacity,
                  ROW_NUMBER() OVER (PARTITION BY date, zone_id ORDER BY peak_occupancy) AS row_num
              FROM (VALUES
                  @Value(accumulated_data)
              ) AS source( date,
                           zone_id,
                           average_occupancy,
                           peak_occupancy,
                           peak_occupancy_time,
                           Capacity)
          ) AS ranked
          WHERE row_num = 1
      )


      MERGE INTO [dbo].[Daily_Occupancy_Stats] AS target
      USING UniqueSource AS source
      ON (target.date = source.date AND target.zone_id = source.zone_id)
      WHEN MATCHED THEN
          UPDATE SET
              target.average_occupancy = source.average_occupancy,
              target.peak_occupancy = source.peak_occupancy,
              target.peak_occupancy_time = source.peak_occupancy_time
      WHEN NOT MATCHED THEN
          INSERT ( date,
                   zone_id,
                   average_occupancy,
                   peak_occupancy,
                   peak_occupancy_time,
                   Capacity )
          VALUES ( source.date,
                   source.zone_id,
                   source.average_occupancy,
                   source.peak_occupancy,
                   source.peak_occupancy_time,
                   source.Capacity);
GetLatestDayStatsUnivWstBlvd: SQLExecutor
    COMBINE_ATTRS = Result Attributes Only
    COMBINE_GEOM = Initiator Geometry Only
    DATASET = AWS_UBCParking
    EXPOSED_ATTRIBUTE_LIST = date
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      SELECT TOP 1 *
      FROM [Parking].[dbo].[Daily_Occupancy_Stats]
      WHERE zone_id = '1B3D7D69-A1D0-4B8B-B86A-D31F8CFF2B2E'
      ORDER BY date DESC;
    RESULT -> ConvertDayToUnix_2
ConvertDayToUnix_2: PythonCaller
    NEW_ATTRIBUTES = date day_unixtimestamp
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              pass

          def input(self, feature):

              # Convert the date string to a datetime object
              date_time = datetime.datetime.strptime(feature.getAttribute('date'), '%Y%m%d')

              # Convert the datetime object to a UNIX timestamp
              unix_timestamp = int(date_time.timestamp())

              print(f"Date: {feature.getAttribute('date')} -> UNIX Timestamp: {unix_timestamp}")

              feature.setAttribute('day_unixtimestamp', unix_timestamp)

              self.pyoutput(feature)

          def close(self):
              # Dictionary to store timestamps and their corresponding indices

              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> GetAllDataFromLatestDayUnivWstBlvd [INITIATOR]
GetAllDataFromLatestDayUnivWstBlvd: SQLExecutor
    COMBINE_ATTRS = Result Attributes Only
    COMBINE_GEOM = Initiator Geometry Only
    DATASET = AWS_UBCParking
    EXPOSED_ATTRIBUTE_LIST = zone_id,TimezoneId,Capacity,Vehicles,Violations,ViolationsEnforced,TimestampUTC,Timestamp,TimestampUnix
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 60
    OUTPUT_FEATURES_DISPLAY = Schema and Data Features
    SQL_STATEMENT:
      SELECT DISTINCT *
      FROM [dbo].[UnivWstBlvdParkade_Occupancy]
      WHERE TimestampUnix > @Value(day_unixtimestamp)
    RESULT -> AddDayHour_2
AddDayHour_2: PythonCaller
    HIDE_ATTRIBUTES = Timestamp TimestampUnix TimestampUTC TimezoneId Violations ViolationsEnforced zone_id
    NEW_ATTRIBUTES = Date hour_minute Vehicles Capacity
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.data = []
              pass

          def input(self, feature):
              # Convert UNIX timestamp to a datetime object
              date_time = datetime.datetime.fromtimestamp(feature.getAttribute('TimestampUnix'))

              # Format the datetime object to a string in yyyy-mm-dd format
              formatted_date = date_time.strftime('%Y-%m-%d')

              # Get the hour and minute from the datetime object
              hour_minute = date_time.strftime('%H:%M')

              feature.setAttribute('Date', formatted_date)
              feature.setAttribute('hour_minute', hour_minute)

              self.data.append(feature)
              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CalculateStatsPerDay_2
CalculateStatsPerDay_2: PythonCaller
    GROUP_BY = Date
    HIDE_ATTRIBUTES = Date hour_minute Vehicles
    NEW_ATTRIBUTES = Capacity average_occupancy peak_occupancy peak_occupancy_time date
    PYTHONSOURCE:
      import fme
      import fmeobjects
      import datetime

      def datetime_to_unixtimestamp(date_str, time_str):
          try:
              # Parse date and time strings
              date_obj = datetime.datetime.strptime(date_str, "%Y-%m-%d").date()
              time_obj = datetime.datetime.strptime(time_str, "%H:%M").time()

              # Combine date and time
              datetime_combined = datetime.datetime.combine(date_obj, time_obj)

              # Convert to Unix timestamp
              unix_timestamp = int(datetime_combined.timestamp())
              return unix_timestamp
          except ValueError:
              return None


      class FeatureProcessor(object):
          """Template Class Interface:
          When using this class, make sure its name is set as the value of the 'Class
          to Process Features' transformer parameter.
          """
          def __init__(self):
              """Base constructor for class members."""
              self.norm_occ = 0
              self.n = 0
              self.average_occupancy = 0
              self.peak_occupancy = 0
              self.peak_occupancy_time = 0
              self_capacity = 0
              self.date = ""
              self.today = datetime.date.today()
              pass

          def input(self, feature):
              self.date = feature.getAttribute('Date')

              if datetime.datetime.strptime(self.date, "%Y-%m-%d").date() != self.today:
                  self.norm_occ += feature.getAttribute('Vehicles')
                  self.n += 1
                  self.capacity = feature.getAttribute('Capacity')
                  if(self.peak_occupancy < feature.getAttribute('Vehicles')):
                      self.peak_occupancy = feature.getAttribute('Vehicles')
                      self.peak_occupancy_time = feature.getAttribute('hour_minute')
                  """This method is called for each FME Feature entering the
                  PythonCaller. If knowledge of all input Features is not required for
                  processing, then the processed Feature can be emitted from this method
                  through self.pyoutput(). Otherwise, the input FME Feature should be
                  cached to a list class member and processed in process_group() when
                  'Group by' attributes(s) are specified, or the close() method.

                  :param fmeobjects.FMEFeature feature: FME Feature entering the
                      transformer.
                  """

          def close(self):
              """This method is called once all the FME Features have been processed
              from input().
              """

              pass

          def process_group(self):
              if datetime.datetime.strptime(self.date, "%Y-%m-%d").date() != self.today:
                  self.average_occupancy = self.norm_occ / self.n

                  out_feature = fmeobjects.FMEFeature()
                  out_feature.setAttribute('average_occupancy', int(self.average_occupancy))
                  out_feature.setAttribute('peak_occupancy', self.peak_occupancy)
                  out_feature.setAttribute('peak_occupancy_time', datetime_to_unixtimestamp(str(self.date), str(self.peak_occupancy_time)))
                  out_feature.setAttribute('Capacity', self.capacity)
                  out_feature.setAttribute('date', self.date)
                  self.pyoutput(out_feature)
                  self.peak_occupancy = 0
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CreateSQL_UnivWstBlvd
CreateSQL_UnivWstBlvd: PythonCaller
    HIDE_ATTRIBUTES = average_occupancy Capacity date peak_occupancy peak_occupancy_time
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              average_occupancy = feature.getAttribute('average_occupancy')
              capacity = feature.getAttribute('Capacity')
              date = feature.getAttribute('date')
              peak_occupancy = feature.getAttribute('peak_occupancy')
              peak_occupancy_time = feature.getAttribute('peak_occupancy_time')
              zone_id = '1B3D7D69-A1D0-4B8B-B86A-D31F8CFF2B2E'


              # Concatenate the attributes into a single string
              feature_string = f"'{date}','{zone_id}',{average_occupancy},{peak_occupancy},{peak_occupancy_time},{capacity}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              if(self.accumulated_data):
                  """This method is called once all the FME Features have been processed
                  from input().
                  """
                  self.accumulated_data = self.accumulated_data[:-3]

                  # Create a new output feature with accumulated data
                  out_feature = fmeobjects.FMEFeature()
                  out_feature.setAttribute('accumulated_data', self.accumulated_data.strip())  # Remove trailing space
                  self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewStats_UnivWstBlvd [INITIATOR]
WriteNewStats_UnivWstBlvd: SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      ;WITH UniqueSource AS (
          SELECT   date,
                   zone_id,
                   average_occupancy,
                   peak_occupancy,
                   peak_occupancy_time,
                   Capacity
          FROM (
              SELECT
                   date,
                   zone_id,
                   average_occupancy,
                   peak_occupancy,
                   peak_occupancy_time,
                   Capacity,
                  ROW_NUMBER() OVER (PARTITION BY date, zone_id ORDER BY peak_occupancy) AS row_num
              FROM (VALUES
                  @Value(accumulated_data)
              ) AS source( date,
                           zone_id,
                           average_occupancy,
                           peak_occupancy,
                           peak_occupancy_time,
                           Capacity)
          ) AS ranked
          WHERE row_num = 1
      )


      MERGE INTO [dbo].[Daily_Occupancy_Stats] AS target
      USING UniqueSource AS source
      ON (target.date = source.date AND target.zone_id = source.zone_id)
      WHEN MATCHED THEN
          UPDATE SET
              target.average_occupancy = source.average_occupancy,
              target.peak_occupancy = source.peak_occupancy,
              target.peak_occupancy_time = source.peak_occupancy_time
      WHEN NOT MATCHED THEN
          INSERT ( date,
                   zone_id,
                   average_occupancy,
                   peak_occupancy,
                   peak_occupancy_time,
                   Capacity )
          VALUES ( source.date,
                   source.zone_id,
                   source.average_occupancy,
                   source.peak_occupancy,
                   source.peak_occupancy_time,
                   source.Capacity);
GetLatestDayStatsThunderbird: SQLExecutor
    COMBINE_ATTRS = Result Attributes Only
    COMBINE_GEOM = Initiator Geometry Only
    DATASET = AWS_UBCParking
    EXPOSED_ATTRIBUTE_LIST = date
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      SELECT TOP 1 *
      FROM [Parking].[dbo].[Daily_Occupancy_Stats]
      WHERE zone_id = '7A5B3916-AD6C-445E-A6C5-BC582EB20530'
      ORDER BY date DESC;
    RESULT -> ConvertDayToUnix_3
ConvertDayToUnix_3: PythonCaller
    NEW_ATTRIBUTES = date day_unixtimestamp
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              pass

          def input(self, feature):

              # Convert the date string to a datetime object
              date_time = datetime.datetime.strptime(feature.getAttribute('date'), '%Y%m%d')

              # Convert the datetime object to a UNIX timestamp
              unix_timestamp = int(date_time.timestamp())

              print(f"Date: {feature.getAttribute('date')} -> UNIX Timestamp: {unix_timestamp}")

              feature.setAttribute('day_unixtimestamp', unix_timestamp)

              self.pyoutput(feature)

          def close(self):
              # Dictionary to store timestamps and their corresponding indices

              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> GetAllDataFromLatestDayThunderbird [INITIATOR]
GetAllDataFromLatestDayThunderbird: SQLExecutor
    COMBINE_ATTRS = Result Attributes Only
    COMBINE_GEOM = Initiator Geometry Only
    DATASET = AWS_UBCParking
    EXPOSED_ATTRIBUTE_LIST = zone_id,TimezoneId,Capacity,Vehicles,Violations,ViolationsEnforced,TimestampUTC,Timestamp,TimestampUnix
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 60
    OUTPUT_FEATURES_DISPLAY = Schema and Data Features
    SQL_STATEMENT:
      SELECT DISTINCT *
      FROM [dbo].[ThunderbirdParkade_Occupancy]
      WHERE TimestampUnix > @Value(day_unixtimestamp)
    RESULT -> AddDayHour_3
AddDayHour_3: PythonCaller
    HIDE_ATTRIBUTES = Timestamp TimestampUnix TimestampUTC TimezoneId Violations ViolationsEnforced zone_id
    NEW_ATTRIBUTES = Date hour_minute Vehicles Capacity
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.data = []
              pass

          def input(self, feature):
              # Convert UNIX timestamp to a datetime object
              date_time = datetime.datetime.fromtimestamp(feature.getAttribute('TimestampUnix'))

              # Format the datetime object to a string in yyyy-mm-dd format
              formatted_date = date_time.strftime('%Y-%m-%d')

              # Get the hour and minute from the datetime object
              hour_minute = date_time.strftime('%H:%M')

              feature.setAttribute('Date', formatted_date)
              feature.setAttribute('hour_minute', hour_minute)

              self.data.append(feature)
              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CalculateStatsPerDay_3
CalculateStatsPerDay_3: PythonCaller
    GROUP_BY = Date
    HIDE_ATTRIBUTES = Date hour_minute Vehicles
    NEW_ATTRIBUTES = Capacity average_occupancy peak_occupancy peak_occupancy_time date
    PYTHONSOURCE:
      import fme
      import fmeobjects
      import datetime

      def datetime_to_unixtimestamp(date_str, time_str):
          try:
              # Parse date and time strings
              date_obj = datetime.datetime.strptime(date_str, "%Y-%m-%d").date()
              time_obj = datetime.datetime.strptime(time_str, "%H:%M").time()

              # Combine date and time
              datetime_combined = datetime.datetime.combine(date_obj, time_obj)

              # Convert to Unix timestamp
              unix_timestamp = int(datetime_combined.timestamp())
              return unix_timestamp
          except ValueError:
              return None


      class FeatureProcessor(object):
          """Template Class Interface:
          When using this class, make sure its name is set as the value of the 'Class
          to Process Features' transformer parameter.
          """
          def __init__(self):
              """Base constructor for class members."""
              self.norm_occ = 0
              self.n = 0
              self.average_occupancy = 0
              self.peak_occupancy = 0
              self.peak_occupancy_time = 0
              self_capacity = 0
              self.date = ""
              self.today = datetime.date.today()
              pass

          def input(self, feature):
              self.date = feature.getAttribute('Date')

              if datetime.datetime.strptime(self.date, "%Y-%m-%d").date() != self.today:
                  self.norm_occ += feature.getAttribute('Vehicles')
                  self.n += 1
                  self.capacity = feature.getAttribute('Capacity')
                  if(self.peak_occupancy < feature.getAttribute('Vehicles')):
                      self.peak_occupancy = feature.getAttribute('Vehicles')
                      self.peak_occupancy_time = feature.getAttribute('hour_minute')
                  """This method is called for each FME Feature entering the
                  PythonCaller. If knowledge of all input Features is not required for
                  processing, then the processed Feature can be emitted from this method
                  through self.pyoutput(). Otherwise, the input FME Feature should be
                  cached to a list class member and processed in process_group() when
                  'Group by' attributes(s) are specified, or the close() method.

                  :param fmeobjects.FMEFeature feature: FME Feature entering the
                      transformer.
                  """

          def close(self):
              """This method is called once all the FME Features have been processed
              from input().
              """

              pass

          def process_group(self):
              if datetime.datetime.strptime(self.date, "%Y-%m-%d").date() != self.today:
                  self.average_occupancy = self.norm_occ / self.n

                  out_feature = fmeobjects.FMEFeature()
                  out_feature.setAttribute('average_occupancy', int(self.average_occupancy))
                  out_feature.setAttribute('peak_occupancy', self.peak_occupancy)
                  out_feature.setAttribute('peak_occupancy_time', datetime_to_unixtimestamp(str(self.date), str(self.peak_occupancy_time)))
                  out_feature.setAttribute('Capacity', self.capacity)
                  out_feature.setAttribute('date', self.date)
                  self.pyoutput(out_feature)
                  self.peak_occupancy = 0
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CreateSQL_Thunderbird
CreateSQL_Thunderbird: PythonCaller
    HIDE_ATTRIBUTES = average_occupancy Capacity date peak_occupancy peak_occupancy_time
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              average_occupancy = feature.getAttribute('average_occupancy')
              capacity = feature.getAttribute('Capacity')
              date = feature.getAttribute('date')
              peak_occupancy = feature.getAttribute('peak_occupancy')
              peak_occupancy_time = feature.getAttribute('peak_occupancy_time')
              zone_id = '7A5B3916-AD6C-445E-A6C5-BC582EB20530'


              # Concatenate the attributes into a single string
              feature_string = f"'{date}','{zone_id}',{average_occupancy},{peak_occupancy},{peak_occupancy_time},{capacity}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              if(self.accumulated_data):
                  """This method is called once all the FME Features have been processed
                  from input().
                  """
                  self.accumulated_data = self.accumulated_data[:-3]

                  # Create a new output feature with accumulated data
                  out_feature = fmeobjects.FMEFeature()
                  out_feature.setAttribute('accumulated_data', self.accumulated_data.strip())  # Remove trailing space
                  self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewStats_Thunderbird [INITIATOR]
WriteNewStats_Thunderbird: SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      ;WITH UniqueSource AS (
          SELECT   date,
                   zone_id,
                   average_occupancy,
                   peak_occupancy,
                   peak_occupancy_time,
                   Capacity
          FROM (
              SELECT
                   date,
                   zone_id,
                   average_occupancy,
                   peak_occupancy,
                   peak_occupancy_time,
                   Capacity,
                  ROW_NUMBER() OVER (PARTITION BY date, zone_id ORDER BY peak_occupancy) AS row_num
              FROM (VALUES
                  @Value(accumulated_data)
              ) AS source( date,
                           zone_id,
                           average_occupancy,
                           peak_occupancy,
                           peak_occupancy_time,
                           Capacity)
          ) AS ranked
          WHERE row_num = 1
      )


      MERGE INTO [dbo].[Daily_Occupancy_Stats] AS target
      USING UniqueSource AS source
      ON (target.date = source.date AND target.zone_id = source.zone_id)
      WHEN MATCHED THEN
          UPDATE SET
              target.average_occupancy = source.average_occupancy,
              target.peak_occupancy = source.peak_occupancy,
              target.peak_occupancy_time = source.peak_occupancy_time
      WHEN NOT MATCHED THEN
          INSERT ( date,
                   zone_id,
                   average_occupancy,
                   peak_occupancy,
                   peak_occupancy_time,
                   Capacity )
          VALUES ( source.date,
                   source.zone_id,
                   source.average_occupancy,
                   source.peak_occupancy,
                   source.peak_occupancy_time,
                   source.Capacity);
GetLatestDayStatsRoseGarden: SQLExecutor
    COMBINE_ATTRS = Result Attributes Only
    COMBINE_GEOM = Initiator Geometry Only
    DATASET = AWS_UBCParking
    EXPOSED_ATTRIBUTE_LIST = date
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      SELECT TOP 1 *
      FROM [Parking].[dbo].[Daily_Occupancy_Stats]
      WHERE zone_id = '33B31206-E1F8-44CE-87A5-318C6D198416'
      ORDER BY date DESC;
    RESULT -> ConvertDayToUnix_4
ConvertDayToUnix_4: PythonCaller
    NEW_ATTRIBUTES = date day_unixtimestamp
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              pass

          def input(self, feature):

              # Convert the date string to a datetime object
              date_time = datetime.datetime.strptime(feature.getAttribute('date'), '%Y%m%d')

              # Convert the datetime object to a UNIX timestamp
              unix_timestamp = int(date_time.timestamp())

              print(f"Date: {feature.getAttribute('date')} -> UNIX Timestamp: {unix_timestamp}")

              feature.setAttribute('day_unixtimestamp', unix_timestamp)

              self.pyoutput(feature)

          def close(self):
              # Dictionary to store timestamps and their corresponding indices

              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> GetAllDataFromLatestDayRoseGarden [INITIATOR]
GetAllDataFromLatestDayRoseGarden: SQLExecutor
    COMBINE_ATTRS = Result Attributes Only
    COMBINE_GEOM = Initiator Geometry Only
    DATASET = AWS_UBCParking
    EXPOSED_ATTRIBUTE_LIST = zone_id,TimezoneId,Capacity,Vehicles,Violations,ViolationsEnforced,TimestampUTC,Timestamp,TimestampUnix
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 60
    OUTPUT_FEATURES_DISPLAY = Schema and Data Features
    SQL_STATEMENT:
      SELECT DISTINCT *
      FROM [dbo].[RoseGardenParkade_Occupancy]
      WHERE TimestampUnix > @Value(day_unixtimestamp)
    RESULT -> AddDayHour_4
AddDayHour_4: PythonCaller
    HIDE_ATTRIBUTES = Timestamp TimestampUnix TimestampUTC TimezoneId Violations ViolationsEnforced zone_id
    NEW_ATTRIBUTES = Date hour_minute Vehicles Capacity
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.data = []
              pass

          def input(self, feature):
              # Convert UNIX timestamp to a datetime object
              date_time = datetime.datetime.fromtimestamp(feature.getAttribute('TimestampUnix'))

              # Format the datetime object to a string in yyyy-mm-dd format
              formatted_date = date_time.strftime('%Y-%m-%d')

              # Get the hour and minute from the datetime object
              hour_minute = date_time.strftime('%H:%M')

              feature.setAttribute('Date', formatted_date)
              feature.setAttribute('hour_minute', hour_minute)

              self.data.append(feature)
              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CalculateStatsPerDay_4
CalculateStatsPerDay_4: PythonCaller
    GROUP_BY = Date
    HIDE_ATTRIBUTES = Date hour_minute Vehicles
    NEW_ATTRIBUTES = Capacity average_occupancy peak_occupancy peak_occupancy_time date
    PYTHONSOURCE:
      import fme
      import fmeobjects
      import datetime

      def datetime_to_unixtimestamp(date_str, time_str):
          try:
              # Parse date and time strings
              date_obj = datetime.datetime.strptime(date_str, "%Y-%m-%d").date()
              time_obj = datetime.datetime.strptime(time_str, "%H:%M").time()

              # Combine date and time
              datetime_combined = datetime.datetime.combine(date_obj, time_obj)

              # Convert to Unix timestamp
              unix_timestamp = int(datetime_combined.timestamp())
              return unix_timestamp
          except ValueError:
              return None


      class FeatureProcessor(object):
          """Template Class Interface:
          When using this class, make sure its name is set as the value of the 'Class
          to Process Features' transformer parameter.
          """
          def __init__(self):
              """Base constructor for class members."""
              self.norm_occ = 0
              self.n = 0
              self.average_occupancy = 0
              self.peak_occupancy = 0
              self.peak_occupancy_time = 0
              self_capacity = 0
              self.date = ""
              self.today = datetime.date.today()
              pass

          def input(self, feature):
              self.date = feature.getAttribute('Date')

              if datetime.datetime.strptime(self.date, "%Y-%m-%d").date() != self.today:
                  self.norm_occ += feature.getAttribute('Vehicles')
                  self.n += 1
                  self.capacity = feature.getAttribute('Capacity')
                  if(self.peak_occupancy < feature.getAttribute('Vehicles')):
                      self.peak_occupancy = feature.getAttribute('Vehicles')
                      self.peak_occupancy_time = feature.getAttribute('hour_minute')
                  """This method is called for each FME Feature entering the
                  PythonCaller. If knowledge of all input Features is not required for
                  processing, then the processed Feature can be emitted from this method
                  through self.pyoutput(). Otherwise, the input FME Feature should be
                  cached to a list class member and processed in process_group() when
                  'Group by' attributes(s) are specified, or the close() method.

                  :param fmeobjects.FMEFeature feature: FME Feature entering the
                      transformer.
                  """

          def close(self):
              """This method is called once all the FME Features have been processed
              from input().
              """

              pass

          def process_group(self):
              if datetime.datetime.strptime(self.date, "%Y-%m-%d").date() != self.today:
                  self.average_occupancy = self.norm_occ / self.n

                  out_feature = fmeobjects.FMEFeature()
                  out_feature.setAttribute('average_occupancy', int(self.average_occupancy))
                  out_feature.setAttribute('peak_occupancy', self.peak_occupancy)
                  out_feature.setAttribute('peak_occupancy_time', datetime_to_unixtimestamp(str(self.date), str(self.peak_occupancy_time)))
                  out_feature.setAttribute('Capacity', self.capacity)
                  out_feature.setAttribute('date', self.date)
                  self.pyoutput(out_feature)
                  self.peak_occupancy = 0
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CreateSQL_RoseGarden
CreateSQL_RoseGarden: PythonCaller
    HIDE_ATTRIBUTES = average_occupancy Capacity date peak_occupancy peak_occupancy_time
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              average_occupancy = feature.getAttribute('average_occupancy')
              capacity = feature.getAttribute('Capacity')
              date = feature.getAttribute('date')
              peak_occupancy = feature.getAttribute('peak_occupancy')
              peak_occupancy_time = feature.getAttribute('peak_occupancy_time')
              zone_id = '33B31206-E1F8-44CE-87A5-318C6D198417'


              # Concatenate the attributes into a single string
              feature_string = f"'{date}','{zone_id}',{average_occupancy},{peak_occupancy},{peak_occupancy_time},{capacity}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              if(self.accumulated_data):
                  """This method is called once all the FME Features have been processed
                  from input().
                  """
                  self.accumulated_data = self.accumulated_data[:-3]

                  # Create a new output feature with accumulated data
                  out_feature = fmeobjects.FMEFeature()
                  out_feature.setAttribute('accumulated_data', self.accumulated_data.strip())  # Remove trailing space
                  self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewStats_RoseGarden [INITIATOR]
WriteNewStats_RoseGarden: SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      ;WITH UniqueSource AS (
          SELECT   date,
                   zone_id,
                   average_occupancy,
                   peak_occupancy,
                   peak_occupancy_time,
                   Capacity
          FROM (
              SELECT
                   date,
                   zone_id,
                   average_occupancy,
                   peak_occupancy,
                   peak_occupancy_time,
                   Capacity,
                  ROW_NUMBER() OVER (PARTITION BY date, zone_id ORDER BY peak_occupancy) AS row_num
              FROM (VALUES
                  @Value(accumulated_data)
              ) AS source( date,
                           zone_id,
                           average_occupancy,
                           peak_occupancy,
                           peak_occupancy_time,
                           Capacity)
          ) AS ranked
          WHERE row_num = 1
      )


      MERGE INTO [dbo].[Daily_Occupancy_Stats] AS target
      USING UniqueSource AS source
      ON (target.date = source.date AND target.zone_id = source.zone_id)
      WHEN MATCHED THEN
          UPDATE SET
              target.average_occupancy = source.average_occupancy,
              target.peak_occupancy = source.peak_occupancy,
              target.peak_occupancy_time = source.peak_occupancy_time
      WHEN NOT MATCHED THEN
          INSERT ( date,
                   zone_id,
                   average_occupancy,
                   peak_occupancy,
                   peak_occupancy_time,
                   Capacity )
          VALUES ( source.date,
                   source.zone_id,
                   source.average_occupancy,
                   source.peak_occupancy,
                   source.peak_occupancy_time,
                   source.Capacity);
GetLatestDayStatsNorth: SQLExecutor
    COMBINE_ATTRS = Result Attributes Only
    COMBINE_GEOM = Initiator Geometry Only
    DATASET = AWS_UBCParking
    EXPOSED_ATTRIBUTE_LIST = date
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      SELECT TOP 1 *
      FROM [Parking].[dbo].[Daily_Occupancy_Stats]
      WHERE zone_id = 'ACF9CF85-6991-42B9-9467-6094008D1094'
      ORDER BY date DESC;
    RESULT -> ConvertDayToUnix_5
ConvertDayToUnix_5: PythonCaller
    NEW_ATTRIBUTES = date day_unixtimestamp
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              pass

          def input(self, feature):

              # Convert the date string to a datetime object
              date_time = datetime.datetime.strptime(feature.getAttribute('date'), '%Y%m%d')

              # Convert the datetime object to a UNIX timestamp
              unix_timestamp = int(date_time.timestamp())

              print(f"Date: {feature.getAttribute('date')} -> UNIX Timestamp: {unix_timestamp}")

              feature.setAttribute('day_unixtimestamp', unix_timestamp)

              self.pyoutput(feature)

          def close(self):
              # Dictionary to store timestamps and their corresponding indices

              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> GetAllDataFromLatestDayNorth [INITIATOR]
GetAllDataFromLatestDayNorth: SQLExecutor
    COMBINE_ATTRS = Result Attributes Only
    COMBINE_GEOM = Initiator Geometry Only
    DATASET = AWS_UBCParking
    EXPOSED_ATTRIBUTE_LIST = zone_id,TimezoneId,Capacity,Vehicles,Violations,ViolationsEnforced,TimestampUTC,Timestamp,TimestampUnix
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 60
    OUTPUT_FEATURES_DISPLAY = Schema and Data Features
    SQL_STATEMENT:
      SELECT DISTINCT *
      FROM [dbo].[NorthParkade_Occupancy]
      WHERE TimestampUnix > @Value(day_unixtimestamp)
    RESULT -> AddDayHour_5
AddDayHour_5: PythonCaller
    HIDE_ATTRIBUTES = Timestamp TimestampUnix TimestampUTC TimezoneId Violations ViolationsEnforced zone_id
    NEW_ATTRIBUTES = Date hour_minute Vehicles Capacity
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.data = []
              pass

          def input(self, feature):
              # Convert UNIX timestamp to a datetime object
              date_time = datetime.datetime.fromtimestamp(feature.getAttribute('TimestampUnix'))

              # Format the datetime object to a string in yyyy-mm-dd format
              formatted_date = date_time.strftime('%Y-%m-%d')

              # Get the hour and minute from the datetime object
              hour_minute = date_time.strftime('%H:%M')

              feature.setAttribute('Date', formatted_date)
              feature.setAttribute('hour_minute', hour_minute)

              self.data.append(feature)
              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CalculateStatsPerDay_5
CalculateStatsPerDay_5: PythonCaller
    GROUP_BY = Date
    HIDE_ATTRIBUTES = Date hour_minute Vehicles
    NEW_ATTRIBUTES = Capacity average_occupancy peak_occupancy peak_occupancy_time date
    PYTHONSOURCE:
      import fme
      import fmeobjects
      import datetime

      def datetime_to_unixtimestamp(date_str, time_str):
          try:
              # Parse date and time strings
              date_obj = datetime.datetime.strptime(date_str, "%Y-%m-%d").date()
              time_obj = datetime.datetime.strptime(time_str, "%H:%M").time()

              # Combine date and time
              datetime_combined = datetime.datetime.combine(date_obj, time_obj)

              # Convert to Unix timestamp
              unix_timestamp = int(datetime_combined.timestamp())
              return unix_timestamp
          except ValueError:
              return None


      class FeatureProcessor(object):
          """Template Class Interface:
          When using this class, make sure its name is set as the value of the 'Class
          to Process Features' transformer parameter.
          """
          def __init__(self):
              """Base constructor for class members."""
              self.norm_occ = 0
              self.n = 0
              self.average_occupancy = 0
              self.peak_occupancy = 0
              self.peak_occupancy_time = 0
              self_capacity = 0
              self.date = ""
              self.today = datetime.date.today()
              pass

          def input(self, feature):
              self.date = feature.getAttribute('Date')

              if datetime.datetime.strptime(self.date, "%Y-%m-%d").date() != self.today:
                  self.norm_occ += feature.getAttribute('Vehicles')
                  self.n += 1
                  self.capacity = feature.getAttribute('Capacity')
                  if(self.peak_occupancy < feature.getAttribute('Vehicles')):
                      self.peak_occupancy = feature.getAttribute('Vehicles')
                      self.peak_occupancy_time = feature.getAttribute('hour_minute')
                  """This method is called for each FME Feature entering the
                  PythonCaller. If knowledge of all input Features is not required for
                  processing, then the processed Feature can be emitted from this method
                  through self.pyoutput(). Otherwise, the input FME Feature should be
                  cached to a list class member and processed in process_group() when
                  'Group by' attributes(s) are specified, or the close() method.

                  :param fmeobjects.FMEFeature feature: FME Feature entering the
                      transformer.
                  """

          def close(self):
              """This method is called once all the FME Features have been processed
              from input().
              """

              pass

          def process_group(self):
              if datetime.datetime.strptime(self.date, "%Y-%m-%d").date() != self.today:
                  self.average_occupancy = self.norm_occ / self.n

                  out_feature = fmeobjects.FMEFeature()
                  out_feature.setAttribute('average_occupancy', int(self.average_occupancy))
                  out_feature.setAttribute('peak_occupancy', self.peak_occupancy)
                  out_feature.setAttribute('peak_occupancy_time', datetime_to_unixtimestamp(str(self.date), str(self.peak_occupancy_time)))
                  out_feature.setAttribute('Capacity', self.capacity)
                  out_feature.setAttribute('date', self.date)
                  self.pyoutput(out_feature)
                  self.peak_occupancy = 0
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CreateSQL_North
CreateSQL_North: PythonCaller
    HIDE_ATTRIBUTES = average_occupancy Capacity date peak_occupancy peak_occupancy_time
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              average_occupancy = feature.getAttribute('average_occupancy')
              capacity = feature.getAttribute('Capacity')
              date = feature.getAttribute('date')
              peak_occupancy = feature.getAttribute('peak_occupancy')
              peak_occupancy_time = feature.getAttribute('peak_occupancy_time')
              zone_id = 'ACF9CF85-6991-42B9-9467-6094008D1094'


              # Concatenate the attributes into a single string
              feature_string = f"'{date}','{zone_id}',{average_occupancy},{peak_occupancy},{peak_occupancy_time},{capacity}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              if(self.accumulated_data):
                  """This method is called once all the FME Features have been processed
                  from input().
                  """
                  self.accumulated_data = self.accumulated_data[:-3]

                  # Create a new output feature with accumulated data
                  out_feature = fmeobjects.FMEFeature()
                  out_feature.setAttribute('accumulated_data', self.accumulated_data.strip())  # Remove trailing space
                  self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewStats_North [INITIATOR]
WriteNewStats_North: SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      ;WITH UniqueSource AS (
          SELECT   date,
                   zone_id,
                   average_occupancy,
                   peak_occupancy,
                   peak_occupancy_time,
                   Capacity
          FROM (
              SELECT
                   date,
                   zone_id,
                   average_occupancy,
                   peak_occupancy,
                   peak_occupancy_time,
                   Capacity,
                  ROW_NUMBER() OVER (PARTITION BY date, zone_id ORDER BY peak_occupancy) AS row_num
              FROM (VALUES
                  @Value(accumulated_data)
              ) AS source( date,
                           zone_id,
                           average_occupancy,
                           peak_occupancy,
                           peak_occupancy_time,
                           Capacity)
          ) AS ranked
          WHERE row_num = 1
      )


      MERGE INTO [dbo].[Daily_Occupancy_Stats] AS target
      USING UniqueSource AS source
      ON (target.date = source.date AND target.zone_id = source.zone_id)
      WHEN MATCHED THEN
          UPDATE SET
              target.average_occupancy = source.average_occupancy,
              target.peak_occupancy = source.peak_occupancy,
              target.peak_occupancy_time = source.peak_occupancy_time
      WHEN NOT MATCHED THEN
          INSERT ( date,
                   zone_id,
                   average_occupancy,
                   peak_occupancy,
                   peak_occupancy_time,
                   Capacity )
          VALUES ( source.date,
                   source.zone_id,
                   source.average_occupancy,
                   source.peak_occupancy,
                   source.peak_occupancy_time,
                   source.Capacity);
GetLatestDayStatsHealthSciences: SQLExecutor
    COMBINE_ATTRS = Result Attributes Only
    COMBINE_GEOM = Initiator Geometry Only
    DATASET = AWS_UBCParking
    EXPOSED_ATTRIBUTE_LIST = date
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      SELECT TOP 1 *
      FROM [Parking].[dbo].[Daily_Occupancy_Stats]
      WHERE zone_id = '859835AD-E855-4DBF-83ED-419DEF40537C'
      ORDER BY date DESC;
    RESULT -> ConvertDayToUnix_6
ConvertDayToUnix_6: PythonCaller
    NEW_ATTRIBUTES = date day_unixtimestamp
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              pass

          def input(self, feature):

              # Convert the date string to a datetime object
              date_time = datetime.datetime.strptime(feature.getAttribute('date'), '%Y%m%d')

              # Convert the datetime object to a UNIX timestamp
              unix_timestamp = int(date_time.timestamp())

              print(f"Date: {feature.getAttribute('date')} -> UNIX Timestamp: {unix_timestamp}")

              feature.setAttribute('day_unixtimestamp', unix_timestamp)

              self.pyoutput(feature)

          def close(self):
              # Dictionary to store timestamps and their corresponding indices

              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> GetAllDataFromLatestDayHealthSciences [INITIATOR]
GetAllDataFromLatestDayHealthSciences: SQLExecutor
    COMBINE_ATTRS = Result Attributes Only
    COMBINE_GEOM = Initiator Geometry Only
    DATASET = AWS_UBCParking
    EXPOSED_ATTRIBUTE_LIST = zone_id,TimezoneId,Capacity,Vehicles,Violations,ViolationsEnforced,TimestampUTC,Timestamp,TimestampUnix
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 60
    OUTPUT_FEATURES_DISPLAY = Schema and Data Features
    SQL_STATEMENT:
      SELECT DISTINCT *
      FROM [dbo].[HealthSciencesParkade_Occupancy]
      WHERE TimestampUnix > @Value(day_unixtimestamp)
    RESULT -> AddDayHour_6
AddDayHour_6: PythonCaller
    HIDE_ATTRIBUTES = Timestamp TimestampUnix TimestampUTC TimezoneId Violations ViolationsEnforced zone_id
    NEW_ATTRIBUTES = Date hour_minute Vehicles Capacity
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.data = []
              pass

          def input(self, feature):
              # Convert UNIX timestamp to a datetime object
              date_time = datetime.datetime.fromtimestamp(feature.getAttribute('TimestampUnix'))

              # Format the datetime object to a string in yyyy-mm-dd format
              formatted_date = date_time.strftime('%Y-%m-%d')

              # Get the hour and minute from the datetime object
              hour_minute = date_time.strftime('%H:%M')

              feature.setAttribute('Date', formatted_date)
              feature.setAttribute('hour_minute', hour_minute)

              self.data.append(feature)
              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CalculateStatsPerDay_6
CalculateStatsPerDay_6: PythonCaller
    GROUP_BY = Date
    HIDE_ATTRIBUTES = Date hour_minute Vehicles
    NEW_ATTRIBUTES = Capacity average_occupancy peak_occupancy peak_occupancy_time date
    PYTHONSOURCE:
      import fme
      import fmeobjects
      import datetime

      def datetime_to_unixtimestamp(date_str, time_str):
          try:
              # Parse date and time strings
              date_obj = datetime.datetime.strptime(date_str, "%Y-%m-%d").date()
              time_obj = datetime.datetime.strptime(time_str, "%H:%M").time()

              # Combine date and time
              datetime_combined = datetime.datetime.combine(date_obj, time_obj)

              # Convert to Unix timestamp
              unix_timestamp = int(datetime_combined.timestamp())
              return unix_timestamp
          except ValueError:
              return None


      class FeatureProcessor(object):
          """Template Class Interface:
          When using this class, make sure its name is set as the value of the 'Class
          to Process Features' transformer parameter.
          """
          def __init__(self):
              """Base constructor for class members."""
              self.norm_occ = 0
              self.n = 0
              self.average_occupancy = 0
              self.peak_occupancy = 0
              self.peak_occupancy_time = 0
              self_capacity = 0
              self.date = ""
              self.today = datetime.date.today()
              pass

          def input(self, feature):
              self.date = feature.getAttribute('Date')

              if datetime.datetime.strptime(self.date, "%Y-%m-%d").date() != self.today:
                  self.norm_occ += feature.getAttribute('Vehicles')
                  self.n += 1
                  self.capacity = feature.getAttribute('Capacity')
                  if(self.peak_occupancy < feature.getAttribute('Vehicles')):
                      self.peak_occupancy = feature.getAttribute('Vehicles')
                      self.peak_occupancy_time = feature.getAttribute('hour_minute')
                  """This method is called for each FME Feature entering the
                  PythonCaller. If knowledge of all input Features is not required for
                  processing, then the processed Feature can be emitted from this method
                  through self.pyoutput(). Otherwise, the input FME Feature should be
                  cached to a list class member and processed in process_group() when
                  'Group by' attributes(s) are specified, or the close() method.

                  :param fmeobjects.FMEFeature feature: FME Feature entering the
                      transformer.
                  """

          def close(self):
              """This method is called once all the FME Features have been processed
              from input().
              """

              pass

          def process_group(self):
              if datetime.datetime.strptime(self.date, "%Y-%m-%d").date() != self.today:
                  self.average_occupancy = self.norm_occ / self.n

                  out_feature = fmeobjects.FMEFeature()
                  out_feature.setAttribute('average_occupancy', int(self.average_occupancy))
                  out_feature.setAttribute('peak_occupancy', self.peak_occupancy)
                  out_feature.setAttribute('peak_occupancy_time', datetime_to_unixtimestamp(str(self.date), str(self.peak_occupancy_time)))
                  out_feature.setAttribute('Capacity', self.capacity)
                  out_feature.setAttribute('date', self.date)
                  self.pyoutput(out_feature)
                  self.peak_occupancy = 0
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CreateSQL_HealthSciences
CreateSQL_HealthSciences: PythonCaller
    HIDE_ATTRIBUTES = average_occupancy Capacity date peak_occupancy peak_occupancy_time
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              average_occupancy = feature.getAttribute('average_occupancy')
              capacity = feature.getAttribute('Capacity')
              date = feature.getAttribute('date')
              peak_occupancy = feature.getAttribute('peak_occupancy')
              peak_occupancy_time = feature.getAttribute('peak_occupancy_time')
              zone_id = '859835AD-E855-4DBF-83ED-419DEF40537C'


              # Concatenate the attributes into a single string
              feature_string = f"'{date}','{zone_id}',{average_occupancy},{peak_occupancy},{peak_occupancy_time},{capacity}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              if(self.accumulated_data):
                  """This method is called once all the FME Features have been processed
                  from input().
                  """
                  self.accumulated_data = self.accumulated_data[:-3]

                  # Create a new output feature with accumulated data
                  out_feature = fmeobjects.FMEFeature()
                  out_feature.setAttribute('accumulated_data', self.accumulated_data.strip())  # Remove trailing space
                  self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewStats_HealthSciences [INITIATOR]
WriteNewStats_HealthSciences: SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      ;WITH UniqueSource AS (
          SELECT   date,
                   zone_id,
                   average_occupancy,
                   peak_occupancy,
                   peak_occupancy_time,
                   Capacity
          FROM (
              SELECT
                   date,
                   zone_id,
                   average_occupancy,
                   peak_occupancy,
                   peak_occupancy_time,
                   Capacity,
                  ROW_NUMBER() OVER (PARTITION BY date, zone_id ORDER BY peak_occupancy) AS row_num
              FROM (VALUES
                  @Value(accumulated_data)
              ) AS source( date,
                           zone_id,
                           average_occupancy,
                           peak_occupancy,
                           peak_occupancy_time,
                           Capacity)
          ) AS ranked
          WHERE row_num = 1
      )


      MERGE INTO [dbo].[Daily_Occupancy_Stats] AS target
      USING UniqueSource AS source
      ON (target.date = source.date AND target.zone_id = source.zone_id)
      WHEN MATCHED THEN
          UPDATE SET
              target.average_occupancy = source.average_occupancy,
              target.peak_occupancy = source.peak_occupancy,
              target.peak_occupancy_time = source.peak_occupancy_time
      WHEN NOT MATCHED THEN
          INSERT ( date,
                   zone_id,
                   average_occupancy,
                   peak_occupancy,
                   peak_occupancy_time,
                   Capacity )
          VALUES ( source.date,
                   source.zone_id,
                   source.average_occupancy,
                   source.peak_occupancy,
                   source.peak_occupancy_time,
                   source.Capacity);
GetLatestDayStatsFraser: SQLExecutor
    COMBINE_ATTRS = Result Attributes Only
    COMBINE_GEOM = Initiator Geometry Only
    DATASET = AWS_UBCParking
    EXPOSED_ATTRIBUTE_LIST = date
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      SELECT TOP 1 *
      FROM [Parking].[dbo].[Daily_Occupancy_Stats]
      WHERE zone_id = '3B3F3EC1-5D84-4C80-9CAD-2CCC9A9268A4'
      ORDER BY date DESC;
    RESULT -> ConvertDayToUnix_7
ConvertDayToUnix_7: PythonCaller
    NEW_ATTRIBUTES = date day_unixtimestamp
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              pass

          def input(self, feature):

              # Convert the date string to a datetime object
              date_time = datetime.datetime.strptime(feature.getAttribute('date'), '%Y%m%d')

              # Convert the datetime object to a UNIX timestamp
              unix_timestamp = int(date_time.timestamp())

              print(f"Date: {feature.getAttribute('date')} -> UNIX Timestamp: {unix_timestamp}")

              feature.setAttribute('day_unixtimestamp', unix_timestamp)

              self.pyoutput(feature)

          def close(self):
              # Dictionary to store timestamps and their corresponding indices

              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> GetAllDataFromLatestDayFraser [INITIATOR]
GetAllDataFromLatestDayFraser: SQLExecutor
    COMBINE_ATTRS = Result Attributes Only
    COMBINE_GEOM = Initiator Geometry Only
    DATASET = AWS_UBCParking
    EXPOSED_ATTRIBUTE_LIST = zone_id,TimezoneId,Capacity,Vehicles,Violations,ViolationsEnforced,TimestampUTC,Timestamp,TimestampUnix
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 60
    OUTPUT_FEATURES_DISPLAY = Schema and Data Features
    SQL_STATEMENT:
      SELECT DISTINCT *
      FROM [dbo].[FraserParkade_Occupancy]
      WHERE TimestampUnix > @Value(day_unixtimestamp)
    RESULT -> AddDayHour_7
AddDayHour_7: PythonCaller
    HIDE_ATTRIBUTES = Timestamp TimestampUnix TimestampUTC TimezoneId Violations ViolationsEnforced zone_id
    NEW_ATTRIBUTES = Date hour_minute Vehicles Capacity
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.data = []
              pass

          def input(self, feature):
              # Convert UNIX timestamp to a datetime object
              date_time = datetime.datetime.fromtimestamp(feature.getAttribute('TimestampUnix'))

              # Format the datetime object to a string in yyyy-mm-dd format
              formatted_date = date_time.strftime('%Y-%m-%d')

              # Get the hour and minute from the datetime object
              hour_minute = date_time.strftime('%H:%M')

              feature.setAttribute('Date', formatted_date)
              feature.setAttribute('hour_minute', hour_minute)

              self.data.append(feature)
              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CalculateStatsPerDay_7
CalculateStatsPerDay_7: PythonCaller
    GROUP_BY = Date
    HIDE_ATTRIBUTES = Date hour_minute Vehicles
    NEW_ATTRIBUTES = Capacity average_occupancy peak_occupancy peak_occupancy_time date
    PYTHONSOURCE:
      import fme
      import fmeobjects
      import datetime

      def datetime_to_unixtimestamp(date_str, time_str):
          try:
              # Parse date and time strings
              date_obj = datetime.datetime.strptime(date_str, "%Y-%m-%d").date()
              time_obj = datetime.datetime.strptime(time_str, "%H:%M").time()

              # Combine date and time
              datetime_combined = datetime.datetime.combine(date_obj, time_obj)

              # Convert to Unix timestamp
              unix_timestamp = int(datetime_combined.timestamp())
              return unix_timestamp
          except ValueError:
              return None


      class FeatureProcessor(object):
          """Template Class Interface:
          When using this class, make sure its name is set as the value of the 'Class
          to Process Features' transformer parameter.
          """
          def __init__(self):
              """Base constructor for class members."""
              self.norm_occ = 0
              self.n = 0
              self.average_occupancy = 0
              self.peak_occupancy = 0
              self.peak_occupancy_time = 0
              self_capacity = 0
              self.date = ""
              self.today = datetime.date.today()
              pass

          def input(self, feature):
              self.date = feature.getAttribute('Date')

              if datetime.datetime.strptime(self.date, "%Y-%m-%d").date() != self.today:
                  self.norm_occ += feature.getAttribute('Vehicles')
                  self.n += 1
                  self.capacity = feature.getAttribute('Capacity')
                  if(self.peak_occupancy < feature.getAttribute('Vehicles')):
                      self.peak_occupancy = feature.getAttribute('Vehicles')
                      self.peak_occupancy_time = feature.getAttribute('hour_minute')
                  """This method is called for each FME Feature entering the
                  PythonCaller. If knowledge of all input Features is not required for
                  processing, then the processed Feature can be emitted from this method
                  through self.pyoutput(). Otherwise, the input FME Feature should be
                  cached to a list class member and processed in process_group() when
                  'Group by' attributes(s) are specified, or the close() method.

                  :param fmeobjects.FMEFeature feature: FME Feature entering the
                      transformer.
                  """

          def close(self):
              """This method is called once all the FME Features have been processed
              from input().
              """

              pass

          def process_group(self):
              if datetime.datetime.strptime(self.date, "%Y-%m-%d").date() != self.today:
                  self.average_occupancy = self.norm_occ / self.n

                  out_feature = fmeobjects.FMEFeature()
                  out_feature.setAttribute('average_occupancy', int(self.average_occupancy))
                  out_feature.setAttribute('peak_occupancy', self.peak_occupancy)
                  out_feature.setAttribute('peak_occupancy_time', datetime_to_unixtimestamp(str(self.date), str(self.peak_occupancy_time)))
                  out_feature.setAttribute('Capacity', self.capacity)
                  out_feature.setAttribute('date', self.date)
                  self.pyoutput(out_feature)
                  self.peak_occupancy = 0
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CreateSQL_Fraser
CreateSQL_Fraser: PythonCaller
    HIDE_ATTRIBUTES = average_occupancy Capacity date peak_occupancy peak_occupancy_time
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              average_occupancy = feature.getAttribute('average_occupancy')
              capacity = feature.getAttribute('Capacity')
              date = feature.getAttribute('date')
              peak_occupancy = feature.getAttribute('peak_occupancy')
              peak_occupancy_time = feature.getAttribute('peak_occupancy_time')
              zone_id = '3B3F3EC1-5D84-4C80-9CAD-2CCC9A9268A4'


              # Concatenate the attributes into a single string
              feature_string = f"'{date}','{zone_id}',{average_occupancy},{peak_occupancy},{peak_occupancy_time},{capacity}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              if(self.accumulated_data):
                  """This method is called once all the FME Features have been processed
                  from input().
                  """
                  self.accumulated_data = self.accumulated_data[:-3]

                  # Create a new output feature with accumulated data
                  out_feature = fmeobjects.FMEFeature()
                  out_feature.setAttribute('accumulated_data', self.accumulated_data.strip())  # Remove trailing space
                  self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewStats_Fraser [INITIATOR]
WriteNewStats_Fraser: SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      ;WITH UniqueSource AS (
          SELECT   date,
                   zone_id,
                   average_occupancy,
                   peak_occupancy,
                   peak_occupancy_time,
                   Capacity
          FROM (
              SELECT
                   date,
                   zone_id,
                   average_occupancy,
                   peak_occupancy,
                   peak_occupancy_time,
                   Capacity,
                  ROW_NUMBER() OVER (PARTITION BY date, zone_id ORDER BY peak_occupancy) AS row_num
              FROM (VALUES
                  @Value(accumulated_data)
              ) AS source( date,
                           zone_id,
                           average_occupancy,
                           peak_occupancy,
                           peak_occupancy_time,
                           Capacity)
          ) AS ranked
          WHERE row_num = 1
      )


      MERGE INTO [dbo].[Daily_Occupancy_Stats] AS target
      USING UniqueSource AS source
      ON (target.date = source.date AND target.zone_id = source.zone_id)
      WHEN MATCHED THEN
          UPDATE SET
              target.average_occupancy = source.average_occupancy,
              target.peak_occupancy = source.peak_occupancy,
              target.peak_occupancy_time = source.peak_occupancy_time
      WHEN NOT MATCHED THEN
          INSERT ( date,
                   zone_id,
                   average_occupancy,
                   peak_occupancy,
                   peak_occupancy_time,
                   Capacity )
          VALUES ( source.date,
                   source.zone_id,
                   source.average_occupancy,
                   source.peak_occupancy,
                   source.peak_occupancy_time,
                   source.Capacity);
