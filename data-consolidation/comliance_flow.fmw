FME workspace comliance_flow.fmw

Creator
    GEOMTYPE = Geometry Object
    NUM = 1
    CREATED -> GetLastMonday3AM
GetLastMonday3AM: PythonCaller
    NEW_ATTRIBUTES = LastMonday3AM
    PYTHONSOURCE:
      import fme
      import fmeobjects
      from datetime import datetime, timedelta

      def last_monday_3am():
          # Get the current date and time
          now = datetime.now()

          # Calculate the last Monday
          last_monday = now - timedelta(days=now.weekday())

          # Set the time to 3 AM
          last_monday_3am = last_monday.replace(hour=3, minute=0, second=0, microsecond=0)

          # Return the formatted date and time string
          return last_monday_3am.strftime('%Y-%m-%d %H:%M:%S')


      class FeatureProcessor(object):
          """Template Class Interface:
          When using this class, make sure its name is set as the value of the 'Class
          to Process Features' transformer parameter.
          """

          def __init__(self):
              """Base constructor for class members."""

              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """

          def close(self):
              """This method is called once all the FME Features have been processed
              from input().
              """
              # Calculate last Monday at 3 AM
              date_last_monday_3am = last_monday_3am()

              # Set this value as an attribute on the FME feature
              feature = fmeobjects.FMEFeature()
              feature.setAttribute('LastMonday3AM', date_last_monday_3am)
              self.pyoutput(feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> GetComplianceCountsFromAllParkades [INITIATOR]
GetComplianceCountsFromAllParkades: SQLExecutor
    COMBINE_ATTRS = Result Attributes Only
    COMBINE_GEOM = Initiator Geometry Only
    DATASET = Autovu_UBC
    EXPOSED_ATTRIBUTE_LIST = ParkadeName,Permit,PayStation,HonkApp,Violation,TotalPlates
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = Autovu_UBC
    MSSQL_ADO_QUERY_FEATURE_TYPES_FOR_MERGE_FILTERS = Yes
    OUTPUT_FEATURES_DISPLAY = Schema and Data Features
    SQL_STATEMENT:
      ;WITH FilteredPlates AS (
          SELECT
              Plate,
              TimestampLocal,
              DeviceId,
              Attributes,
              ROW_NUMBER() OVER (PARTITION BY Plate ORDER BY TimestampLocal DESC) AS rn
          FROM
              [LPRManager].[dbo].[Reads]
          WHERE
              TimestampLocal >= '@Value(LastMonday3AM)'
      ),
      LatestPlates AS (
          SELECT
              Plate,
              TimestampLocal,
              DeviceId,
              Attributes
          FROM
              FilteredPlates
          WHERE
              rn = 1
      ),
      EntryDevices AS (
          SELECT *
          FROM (VALUES
              ('2084F4DA-E6EC-4013-9B79-2414D488F804', 'Fraser'),
              ('B4FD97C7-41C8-40F7-9772-759752373A53', 'Fraser'),
              ('68629885-7E9F-4B8F-8306-D1001D36720D', 'HealthSciences'),
              ('EB498796-DD80-46D0-AE40-8DED5983B66D', 'HealthSciences'),
              ('A06921B1-628E-4233-8579-E6701894DC2F', 'HealthSciences'),
              ('584E0CE0-E0BB-4324-B1E0-070950B456AC', 'North'),
              ('5B88D16F-4F3C-4D03-B158-9301BA7F7B95', 'North'),
              ('149ADAA5-7DE2-4EFE-8E04-490DB7B4F8BF', 'North'),
              ('D8DC7032-E6CA-4F09-818C-ABCAFD4E2AFB', 'Rose'),
              ('8AEE758A-C7D5-4B9B-9F3E-8E9D67FBDBE6', 'Rose'),
              ('78474174-61AE-4D8F-8D79-A6DD2B6EEEFA', 'Rose'),
              ('AD848ED9-8191-417E-B7D0-92B410071D17', 'Thunderbird'),
              ('4478A7D4-34D8-46D5-90EA-FD5F6FCD36FB', 'Thunderbird'),
              ('7C72ADB0-8824-4EB3-B16F-B57FCC09BDF3', 'Thunderbird'),
              ('46C5937F-40AE-475A-B6BC-6E24F9CE2BC7', 'UnivWstBlvd'),
              ('20A08C9D-7AF4-40C9-BA2B-53F6F5FC8B79', 'West'),
              ('B828434B-DE54-4FA8-83F4-65461D01FE97', 'West'),
              ('D48B0656-5B5A-4675-A18C-DBAACF916521', 'West')
          ) AS T (DeviceId, ParkadeName)
      ),
      FilteredLatestPlates AS (
          SELECT
              lp.Plate,
              lp.TimestampLocal,
              lp.DeviceId,
              lp.Attributes,
              ed.ParkadeName
          FROM
              LatestPlates lp
          JOIN
              EntryDevices ed ON lp.DeviceId = ed.DeviceId
      ),
      ActivePlates AS (
          SELECT
              Plate,
              ZoneId,
              PermitId,
              EffectiveDate,
              ExpiryDate,
              ROW_NUMBER() OVER (PARTITION BY Plate ORDER BY ExpiryDate DESC) AS rn
          FROM
              [PaybyPlateSync].[dbo].[ActivePlates]
      ),
      ClassifiedPlates AS (
          SELECT
              flp.Plate,
              flp.TimestampLocal,
              flp.DeviceId,
              flp.Attributes,
              flp.ParkadeName,
              ap.ZoneId,
              z.ZoneName,
              ap.PermitId,
              ap.EffectiveDate,
              ap.ExpiryDate,
              CASE
                  WHEN z.ZoneName IS NULL THEN 'Violation'
                  WHEN z.ZoneName LIKE 'T2Systems%' THEN 'Permit'
                  WHEN z.ZoneName LIKE 'DigitalPayment%' THEN 'PayStation'
                  WHEN z.ZoneName LIKE 'GenericRESTService-%' THEN 'Honk App'
                  ELSE 'Unknown'
              END AS ParkingMethod
          FROM
              FilteredLatestPlates flp
          LEFT JOIN
              ActivePlates ap ON flp.Plate = ap.Plate AND ap.rn = 1
          LEFT JOIN
              [PaybyPlateSync].[dbo].[Zones] z ON ap.ZoneId = z.ZoneId
      )
      SELECT
          COALESCE(ParkadeName, 'Total') AS ParkadeName,
          COUNT(CASE WHEN ParkingMethod = 'Permit' THEN 1 END) AS Permit,
          COUNT(CASE WHEN ParkingMethod = 'PayStation' THEN 1 END) AS PayStation,
          COUNT(CASE WHEN ParkingMethod = 'Honk App' THEN 1 END) AS HonkApp,
          COUNT(CASE WHEN ParkingMethod = 'Violation' THEN 1 END) AS Violation,
          COUNT(*) AS TotalPlates
      FROM
          ClassifiedPlates
      GROUP BY
          ROLLUP(ParkadeName)
      ORDER BY
          CASE
              WHEN ParkadeName = 'Total' THEN 1
              ELSE 0
          END,
          ParkadeName;
    RESULT -> Add_LastUpdate
Add_LastUpdate: PythonCaller
    NEW_ATTRIBUTES = LastUpdate ParkadeName HonkApp PayStation Permit Violation TotalPlates
    PYTHONSOURCE:
      import fme
      import fmeobjects
      from datetime import datetime, timedelta

      def get_current_date():
          # Get the current date and time
          current_date = datetime.now()

          # Format the current date as a string
          current_date_str = current_date.strftime('%Y-%m-%d %H:%M:%S')

          return current_date_str

      class FeatureProcessor(object):
          """Template Class Interface:
          When using this class, make sure its name is set as the value of the 'Class
          to Process Features' transformer parameter.
          """

          def __init__(self):
              """Base constructor for class members."""
              self.current_date = get_current_date()
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              feature.setAttribute('LastUpdate', self.current_date)
              self.pyoutput(feature)
              pass

          def close(self):
              """This method is called once all the FME Features have been processed
              from input().
              """

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> ConvertDayToUnix
ConvertDayToUnix: PythonCaller
    NEW_ATTRIBUTES = LastUpdate ParkadeName HonkApp PayStation Permit Violation TotalPlates
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              pass

          def input(self, feature):

              # Convert the date string to a datetime object
              date_time = datetime.datetime.strptime(feature.getAttribute('LastUpdate'), '%Y-%m-%d %H:%M:%S')

              # Convert the datetime object to a UNIX timestamp
              unix_timestamp = int(date_time.timestamp())

              print(f"Date: {feature.getAttribute('LastUpdate')} -> UNIX Timestamp: {unix_timestamp}")

              feature.setAttribute('LastUpdate', unix_timestamp)

              self.pyoutput(feature)

          def close(self):
              # Dictionary to store timestamps and their corresponding indices

              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CreateSQL
CreateSQL: PythonCaller
    HIDE_ATTRIBUTES = LastUpdate HonkApp PayStation Permit Violation TotalPlates ParkadeName
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              ParkadeName   = feature.getAttribute('ParkadeName')
              Permit        = feature.getAttribute('Permit')
              PayStation    = feature.getAttribute('PayStation')
              HonkApp       = feature.getAttribute('HonkApp')
              Violation     = feature.getAttribute('Violation')
              TotalPlates   = feature.getAttribute('TotalPlates')
              LastUpdate    = feature.getAttribute('LastUpdate')

              # Concatenate the attributes into a single string
              feature_string = f"'{ParkadeName}',{Permit},{PayStation},{HonkApp},{Violation},{TotalPlates},{LastUpdate}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              if(self.accumulated_data):
                  """This method is called once all the FME Features have been processed
                  from input().
                  """
                  self.accumulated_data = self.accumulated_data[:-3]

                  # Create a new output feature with accumulated data
                  out_feature = fmeobjects.FMEFeature()
                  out_feature.setAttribute('accumulated_data', self.accumulated_data.strip())  # Remove trailing space
                  self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> SQLExecutor [INITIATOR]
SQLExecutor
    COMBINE_ATTRS = Result Attributes Only
    COMBINE_GEOM = Initiator Geometry Only
    DATASET = ServerTestDB
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT:
      -- Use MERGE to perform the insert or update operation
      MERGE INTO [Parking].[dbo].[CurrentCompliance] AS target
      USING (VALUES @Value(accumulated_data)) AS source (ParkadeName, Permit, PayStation, HonkApp, Violation, TotalPlates, LastUpdate)
      ON (target.ParkadeName = source.ParkadeName)
      WHEN MATCHED THEN
          UPDATE SET
              target.LastUpdate = source.LastUpdate,
              target.HonkApp = source.HonkApp,
              target.PayStation = source.PayStation,
              target.Permit = source.Permit,
              target.Violation = source.Violation,
              target.TotalPlates = source.TotalPlates
      WHEN NOT MATCHED THEN
          INSERT (LastUpdate, ParkadeName, HonkApp, PayStation, Permit, Violation, TotalPlates)
          VALUES (source.LastUpdate, source.ParkadeName, source.HonkApp, source.PayStation, source.Permit, source.Violation, source.TotalPlates);
