FME workspace parking_stats_weekly.fmw

Creator
    GEOMTYPE = Geometry Object
    NUM = 1
    CREATED -> SQLExecutor [INITIATOR]
SQLExecutor
    COMBINE_ATTRS = Result Attributes Only
    COMBINE_GEOM = Initiator Geometry Only
    DATASET = AWS_UBCParking
    EXPOSED_ATTRIBUTE_LIST = parkade_name,zone_id,parkade_capacity,Occupancy_Table_Name
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT = SELECT * FROM [Parking].[dbo].[Parkade_management]
    RESULT -> WestParkade
    RESULT -> UnivWstBlvd
    RESULT -> Thunderbird
    RESULT -> RoseGarden
    RESULT -> North
    RESULT -> HealthSciences
    RESULT -> Fraser
WestParkade: Tester
    BOOL_OP = OR
    TEST_CLAUSE = TEST @Value(parkade_name) = West Parkade
    TEST_MODE = TEST
    PASSED -> GetLatestDayStatsWestParkade [INITIATOR]
GetLatestDayStatsWestParkade: SQLExecutor
    ATTR_IGNORE_NULLS = Yes
    COMBINE_ATTRS = Keep Initiator Attributes if Conflict
    COMBINE_GEOM = Initiator Geometry Only
    DATASET = AWS_UBCParking
    EXPOSED_ATTRIBUTE_LIST = week_start_date,zone_id
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      SELECT TOP 1 *
      FROM [Parking].[dbo].[Weekly_Occupancy_Stats]
      WHERE zone_id = '@Value(zone_id)'
      ORDER BY week_start_date DESC;
    RESULT -> ConvertDayToUnix
ConvertDayToUnix: PythonCaller
    NEW_ATTRIBUTES = week_start_date week_start_date_unixtimestamp Occupancy_Table_Name zone_id
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              pass

          def input(self, feature):

              # Convert the date string to a datetime object
              date_time = datetime.datetime.strptime(feature.getAttribute('week_start_date'), '%Y-%m-%d')

              # Convert the datetime object to a UNIX timestamp
              unix_timestamp = int(date_time.timestamp())

              print(f"Date: {feature.getAttribute('date')} -> UNIX Timestamp: {unix_timestamp}")

              feature.setAttribute('week_start_date_unixtimestamp', unix_timestamp)

              self.pyoutput(feature)

          def close(self):
              # Dictionary to store timestamps and their corresponding indices

              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> GetAllDataFromLatestDayWestParkade [INITIATOR]
GetAllDataFromLatestDayWestParkade: SQLExecutor
    ATTR_IGNORE_NULLS = Yes
    COMBINE_ATTRS = Keep Initiator Attributes if Conflict
    COMBINE_GEOM = Initiator Geometry Only
    DATASET = AWS_UBCParking
    EXPOSED_ATTRIBUTE_LIST = zone_id,TimezoneId,Capacity,Vehicles,Violations,ViolationsEnforced,TimestampUTC,Timestamp,TimestampUnix
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 60
    OUTPUT_FEATURES_DISPLAY = Schema and Data Features
    SQL_STATEMENT:
      SELECT DISTINCT *
      FROM @Value(Occupancy_Table_Name)
      WHERE TimestampUnix > @Value(week_start_date_unixtimestamp)
    RESULT -> AddDayHour
AddDayHour: PythonCaller
    HIDE_ATTRIBUTES = Timestamp TimestampUnix TimestampUTC TimezoneId Violations ViolationsEnforced zone_id
    NEW_ATTRIBUTES = Date hour_minute Vehicles Capacity zone_id
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.data = []
              pass

          def input(self, feature):
              # Convert UNIX timestamp to a datetime object
              date_time = datetime.datetime.fromtimestamp(feature.getAttribute('TimestampUnix'))

              # Format the datetime object to a string in yyyy-mm-dd format
              formatted_date = date_time.strftime('%Y-%m-%d')

              # Get the hour and minute from the datetime object
              hour_minute = date_time.strftime('%H:%M')

              feature.setAttribute('Date', formatted_date)
              feature.setAttribute('hour_minute', hour_minute)

              self.data.append(feature)
              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> AddWeek
AddWeek: PythonCaller
    NEW_ATTRIBUTES = week_start_date week_end_date Date hour_minute Vehicles Capacity zone_id
    PYTHONSOURCE:
      import fme
      import fmeobjects
      import datetime
      import time

      def get_week_bounds(given_date):
          # Ensure given_date is a datetime.date object
          if isinstance(given_date, str):
              given_date = datetime.datetime.strptime(given_date, "%Y-%m-%d").date()
          elif isinstance(given_date, datetime.datetime):
              given_date = given_date.date()

          # Calculate the first and last day of the week
          start_of_week = given_date - datetime.timedelta(days=given_date.weekday())
          end_of_week = start_of_week + datetime.timedelta(days=6)

          return start_of_week, end_of_week

      class FeatureProcessor(object):
          """Template Class Interface:
          When using this class, make sure its name is set as the value of the 'Class
          to Process Features' transformer parameter.
          """

          def __init__(self):
              """Base constructor for class members."""
              pass

          def input(self, feature):
              # Convert UNIX timestamp to a datetime object
              first_date, last_date = get_week_bounds(feature.getAttribute('Date'))

              feature.setAttribute('week_start_date', first_date.strftime('%Y-%m-%d'))
              feature.setAttribute('week_end_date', last_date.strftime('%Y-%m-%d'))

              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CalculateStatsPerWeek
CalculateStatsPerWeek: PythonCaller
    GROUP_BY = week_start_date
    HIDE_ATTRIBUTES = Date hour_minute Vehicles
    NEW_ATTRIBUTES = Capacity average_occupancy peak_occupancy peak_occupancy_time week_start_date week_end_date zone_id
    PYTHONSOURCE:
      import fme
      import fmeobjects
      import datetime

      def get_week_bounds(given_date):
          # Ensure given_date is a datetime.date object
          if isinstance(given_date, str):
              given_date = datetime.datetime.strptime(given_date, "%Y-%m-%d").date()
          elif isinstance(given_date, datetime.datetime):
              given_date = given_date.date()

          # Calculate the first and last day of the week
          start_of_week = given_date - datetime.timedelta(days=given_date.weekday())
          end_of_week = start_of_week + datetime.timedelta(days=6)

          return start_of_week, end_of_week

      def datetime_to_unixtimestamp(date_str, time_str):
          try:
              # Parse date and time strings
              date_obj = datetime.datetime.strptime(date_str, "%Y-%m-%d").date()
              time_obj = datetime.datetime.strptime(time_str, "%H:%M").time()

              # Combine date and time
              datetime_combined = datetime.datetime.combine(date_obj, time_obj)

              # Convert to Unix timestamp
              unix_timestamp = int(datetime_combined.timestamp())
              return unix_timestamp
          except ValueError:
              return None


      class FeatureProcessor(object):
          """Template Class Interface:
          When using this class, make sure its name is set as the value of the 'Class
          to Process Features' transformer parameter.
          """
          def __init__(self):
              """Base constructor for class members."""
              self.norm_occ = 0
              self.n = 0
              self.average_occupancy = 0
              self.peak_occupancy = 0
              self.peak_occupancy_time = 0
              self.capacity = 0
              self.week_start_day = ""
              self.week_end_day = ""
              self.date = ""
              self.current_week_start_day, week_last_day = get_week_bounds(datetime.date.today())
              self.zone_id = ""
              pass

          def input(self, feature):
              self.zone_id = str(feature.getAttribute('zone_id'))
              self.week_start_date = feature.getAttribute('week_start_date')
              self.week_end_date = feature.getAttribute('week_end_date')

              if datetime.datetime.strptime(str(self.current_week_start_day), "%Y-%m-%d").date() != self.week_start_date:
                  self.norm_occ += feature.getAttribute('Vehicles')
                  self.n += 1
                  self.capacity = feature.getAttribute('Capacity')
                  if(self.peak_occupancy < feature.getAttribute('Vehicles')):
                      self.peak_occupancy = feature.getAttribute('Vehicles')
                      self.peak_occupancy_time = feature.getAttribute('hour_minute')
                      self.date = feature.getAttribute('Date')
                  """This method is called for each FME Feature entering the
                  PythonCaller. If knowledge of all input Features is not required for
                  processing, then the processed Feature can be emitted from this method
                  through self.pyoutput(). Otherwise, the input FME Feature should be
                  cached to a list class member and processed in process_group() when
                  'Group by' attributes(s) are specified, or the close() method.

                  :param fmeobjects.FMEFeature feature: FME Feature entering the
                      transformer.
                  """

          def close(self):
              """This method is called once all the FME Features have been processed
              from input().
              """

              pass

          def process_group(self):
              if datetime.datetime.strptime(str(self.current_week_start_day), "%Y-%m-%d").date() != self.week_start_date:
                  self.average_occupancy = self.norm_occ / self.n
                  out_feature = fmeobjects.FMEFeature()
                  out_feature.setAttribute('average_occupancy', int(self.average_occupancy))
                  out_feature.setAttribute('zone_id', self.zone_id)
                  out_feature.setAttribute('peak_occupancy', self.peak_occupancy)
                  out_feature.setAttribute('peak_occupancy_time', datetime_to_unixtimestamp(str(self.date), str(self.peak_occupancy_time)))
                  out_feature.setAttribute('Capacity', self.capacity)
                  out_feature.setAttribute('week_start_date', self.week_start_date)
                  out_feature.setAttribute('week_end_date', self.week_end_date)
                  self.pyoutput(out_feature)
                  self.peak_occupancy = 0
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CreateSQL_WestParkade
CreateSQL_WestParkade: PythonCaller
    HIDE_ATTRIBUTES = average_occupancy Capacity week_start_date week_end_date peak_occupancy peak_occupancy_time
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              average_occupancy = feature.getAttribute('average_occupancy')
              capacity = feature.getAttribute('Capacity')
              week_start_date = feature.getAttribute('week_start_date')
              week_end_date = feature.getAttribute('week_end_date')
              peak_occupancy = feature.getAttribute('peak_occupancy')
              peak_occupancy_time = feature.getAttribute('peak_occupancy_time')
              zone_id = feature.getAttribute('zone_id')


              # Concatenate the attributes into a single string
              feature_string = f"'{week_start_date}','{week_end_date}','{zone_id}',{average_occupancy},{peak_occupancy},{peak_occupancy_time},{capacity}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              """This method is called once all the FME Features have been processed
              from input().
              """
              self.accumulated_data = self.accumulated_data[:-3]

              # Create a new output feature with accumulated data
              out_feature = fmeobjects.FMEFeature()
              out_feature.setAttribute('accumulated_data', self.accumulated_data.strip())  # Remove trailing space
              self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewStats_WestParkade [INITIATOR]
WriteNewStats_WestParkade: SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      ;WITH UniqueSource AS (
          SELECT   week_start_date,
                   week_end_date,
                   zone_id,
                   average_occupancy,
                   peak_occupancy,
                   peak_occupancy_time,
                   Capacity
          FROM (
              SELECT
                   week_start_date,
                   week_end_date,
                   zone_id,
                   average_occupancy,
                   peak_occupancy,
                   peak_occupancy_time,
                   Capacity,
                  ROW_NUMBER() OVER (PARTITION BY week_start_date, zone_id ORDER BY peak_occupancy) AS row_num
              FROM (VALUES
                  @Value(accumulated_data)
              ) AS source( week_start_date,
                           week_end_date,
                           zone_id,
                           average_occupancy,
                           peak_occupancy,
                           peak_occupancy_time,
                           Capacity)
          ) AS ranked
          WHERE row_num = 1
      )



      MERGE INTO [dbo].[Weekly_Occupancy_Stats] AS target
      USING UniqueSource AS source
      ON (target.week_start_date = source.week_start_date AND target.zone_id = source.zone_id)
      WHEN MATCHED THEN
          UPDATE SET
              target.average_occupancy = source.average_occupancy,
              target.peak_occupancy = source.peak_occupancy,
              target.peak_occupancy_time = source.peak_occupancy_time
      WHEN NOT MATCHED THEN
          INSERT ( week_start_date,
                   week_end_date,
                   zone_id,
                   average_occupancy,
                   peak_occupancy,
                   peak_occupancy_time,
                   Capacity )
          VALUES ( source.week_start_date,
                   source.week_end_date,
                   source.zone_id,
                   source.average_occupancy,
                   source.peak_occupancy,
                   source.peak_occupancy_time,
                   source.Capacity);
UnivWstBlvd: Tester
    BOOL_OP = OR
    TEST_CLAUSE = TEST @Value(parkade_name) = University West Boulevard
    TEST_MODE = TEST
    PASSED -> GetLatestDayStatsUnivWstBlvd [INITIATOR]
GetLatestDayStatsUnivWstBlvd: SQLExecutor
    ATTR_IGNORE_NULLS = Yes
    COMBINE_ATTRS = Keep Initiator Attributes if Conflict
    COMBINE_GEOM = Initiator Geometry Only
    DATASET = AWS_UBCParking
    EXPOSED_ATTRIBUTE_LIST = week_start_date,zone_id
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      SELECT TOP 1 *
      FROM [Parking].[dbo].[Weekly_Occupancy_Stats]
      WHERE zone_id = '@Value(zone_id)'
      ORDER BY week_start_date DESC;
    RESULT -> ConvertDayToUnix_2
ConvertDayToUnix_2: PythonCaller
    NEW_ATTRIBUTES = week_start_date week_start_date_unixtimestamp Occupancy_Table_Name zone_id
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              pass

          def input(self, feature):

              # Convert the date string to a datetime object
              date_time = datetime.datetime.strptime(feature.getAttribute('week_start_date'), '%Y-%m-%d')

              # Convert the datetime object to a UNIX timestamp
              unix_timestamp = int(date_time.timestamp())

              print(f"Date: {feature.getAttribute('date')} -> UNIX Timestamp: {unix_timestamp}")

              feature.setAttribute('week_start_date_unixtimestamp', unix_timestamp)

              self.pyoutput(feature)

          def close(self):
              # Dictionary to store timestamps and their corresponding indices

              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> GetAllDataFromLatestDayUnivWstBlvd [INITIATOR]
GetAllDataFromLatestDayUnivWstBlvd: SQLExecutor
    ATTR_IGNORE_NULLS = Yes
    COMBINE_ATTRS = Keep Result Attributes if Conflict
    COMBINE_GEOM = Initiator Geometry Only
    DATASET = AWS_UBCParking
    EXPOSED_ATTRIBUTE_LIST = zone_id,TimezoneId,Capacity,Vehicles,Violations,ViolationsEnforced,TimestampUTC,Timestamp,TimestampUnix
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 60
    OUTPUT_FEATURES_DISPLAY = Schema and Data Features
    SQL_STATEMENT:
      SELECT DISTINCT *
      FROM @Value(Occupancy_Table_Name)
      WHERE TimestampUnix > @Value(week_start_date_unixtimestamp)
    RESULT -> AddDayHour_2
AddDayHour_2: PythonCaller
    HIDE_ATTRIBUTES = Timestamp TimestampUnix TimestampUTC TimezoneId Violations ViolationsEnforced zone_id
    NEW_ATTRIBUTES = Date hour_minute Vehicles Capacity
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.data = []
              pass

          def input(self, feature):
              # Convert UNIX timestamp to a datetime object
              date_time = datetime.datetime.fromtimestamp(feature.getAttribute('TimestampUnix'))

              # Format the datetime object to a string in yyyy-mm-dd format
              formatted_date = date_time.strftime('%Y-%m-%d')

              # Get the hour and minute from the datetime object
              hour_minute = date_time.strftime('%H:%M')

              feature.setAttribute('Date', formatted_date)
              feature.setAttribute('hour_minute', hour_minute)

              self.data.append(feature)
              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> AddWeek_2
AddWeek_2: PythonCaller
    NEW_ATTRIBUTES = week_start_date week_end_date Date hour_minute Vehicles Capacity zone_id
    PYTHONSOURCE:
      import fme
      import fmeobjects
      import datetime
      import time

      def get_week_bounds(given_date):
          # Ensure given_date is a datetime.date object
          if isinstance(given_date, str):
              given_date = datetime.datetime.strptime(given_date, "%Y-%m-%d").date()
          elif isinstance(given_date, datetime.datetime):
              given_date = given_date.date()

          # Calculate the first and last day of the week
          start_of_week = given_date - datetime.timedelta(days=given_date.weekday())
          end_of_week = start_of_week + datetime.timedelta(days=6)

          return start_of_week, end_of_week

      class FeatureProcessor(object):
          """Template Class Interface:
          When using this class, make sure its name is set as the value of the 'Class
          to Process Features' transformer parameter.
          """

          def __init__(self):
              """Base constructor for class members."""
              pass

          def input(self, feature):
              # Convert UNIX timestamp to a datetime object
              first_date, last_date = get_week_bounds(feature.getAttribute('Date'))

              feature.setAttribute('week_start_date', first_date.strftime('%Y-%m-%d'))
              feature.setAttribute('week_end_date', last_date.strftime('%Y-%m-%d'))

              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CalculateStatsPerWeek_2
CalculateStatsPerWeek_2: PythonCaller
    GROUP_BY = week_start_date
    HIDE_ATTRIBUTES = Date hour_minute Vehicles
    NEW_ATTRIBUTES = Capacity average_occupancy peak_occupancy peak_occupancy_time week_start_date week_end_date zone_id
    PYTHONSOURCE:
      import fme
      import fmeobjects
      import datetime

      def get_week_bounds(given_date):
          # Ensure given_date is a datetime.date object
          if isinstance(given_date, str):
              given_date = datetime.datetime.strptime(given_date, "%Y-%m-%d").date()
          elif isinstance(given_date, datetime.datetime):
              given_date = given_date.date()

          # Calculate the first and last day of the week
          start_of_week = given_date - datetime.timedelta(days=given_date.weekday())
          end_of_week = start_of_week + datetime.timedelta(days=6)

          return start_of_week, end_of_week

      def datetime_to_unixtimestamp(date_str, time_str):
          try:
              # Parse date and time strings
              date_obj = datetime.datetime.strptime(date_str, "%Y-%m-%d").date()
              time_obj = datetime.datetime.strptime(time_str, "%H:%M").time()

              # Combine date and time
              datetime_combined = datetime.datetime.combine(date_obj, time_obj)

              # Convert to Unix timestamp
              unix_timestamp = int(datetime_combined.timestamp())
              return unix_timestamp
          except ValueError:
              return None


      class FeatureProcessor(object):
          """Template Class Interface:
          When using this class, make sure its name is set as the value of the 'Class
          to Process Features' transformer parameter.
          """
          def __init__(self):
              """Base constructor for class members."""
              self.norm_occ = 0
              self.n = 0
              self.average_occupancy = 0
              self.peak_occupancy = 0
              self.peak_occupancy_time = 0
              self.capacity = 0
              self.week_start_day = ""
              self.week_end_day = ""
              self.date = ""
              self.current_week_start_day, week_last_day = get_week_bounds(datetime.date.today())
              self.zone_id = ""
              pass

          def input(self, feature):
              self.zone_id = str(feature.getAttribute('zone_id'))
              self.week_start_date = feature.getAttribute('week_start_date')
              self.week_end_date = feature.getAttribute('week_end_date')

              if datetime.datetime.strptime(str(self.current_week_start_day), "%Y-%m-%d").date() != self.week_start_date:
                  self.norm_occ += feature.getAttribute('Vehicles')
                  self.n += 1
                  self.capacity = feature.getAttribute('Capacity')
                  if(self.peak_occupancy < feature.getAttribute('Vehicles')):
                      self.peak_occupancy = feature.getAttribute('Vehicles')
                      self.peak_occupancy_time = feature.getAttribute('hour_minute')
                      self.date = feature.getAttribute('Date')
                  """This method is called for each FME Feature entering the
                  PythonCaller. If knowledge of all input Features is not required for
                  processing, then the processed Feature can be emitted from this method
                  through self.pyoutput(). Otherwise, the input FME Feature should be
                  cached to a list class member and processed in process_group() when
                  'Group by' attributes(s) are specified, or the close() method.

                  :param fmeobjects.FMEFeature feature: FME Feature entering the
                      transformer.
                  """

          def close(self):
              """This method is called once all the FME Features have been processed
              from input().
              """

              pass

          def process_group(self):
              if datetime.datetime.strptime(str(self.current_week_start_day), "%Y-%m-%d").date() != self.week_start_date:
                  self.average_occupancy = self.norm_occ / self.n
                  out_feature = fmeobjects.FMEFeature()
                  out_feature.setAttribute('average_occupancy', int(self.average_occupancy))
                  out_feature.setAttribute('zone_id', self.zone_id)
                  out_feature.setAttribute('peak_occupancy', self.peak_occupancy)
                  out_feature.setAttribute('peak_occupancy_time', datetime_to_unixtimestamp(str(self.date), str(self.peak_occupancy_time)))
                  out_feature.setAttribute('Capacity', self.capacity)
                  out_feature.setAttribute('week_start_date', self.week_start_date)
                  out_feature.setAttribute('week_end_date', self.week_end_date)
                  self.pyoutput(out_feature)
                  self.peak_occupancy = 0
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CreateSQL_UnivWstBlvd
CreateSQL_UnivWstBlvd: PythonCaller
    HIDE_ATTRIBUTES = average_occupancy Capacity week_start_date week_end_date peak_occupancy peak_occupancy_time
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              average_occupancy = feature.getAttribute('average_occupancy')
              capacity = feature.getAttribute('Capacity')
              week_start_date = feature.getAttribute('week_start_date')
              week_end_date = feature.getAttribute('week_end_date')
              peak_occupancy = feature.getAttribute('peak_occupancy')
              peak_occupancy_time = feature.getAttribute('peak_occupancy_time')
              zone_id = feature.getAttribute('zone_id')


              # Concatenate the attributes into a single string
              feature_string = f"'{week_start_date}','{week_end_date}','{zone_id}',{average_occupancy},{peak_occupancy},{peak_occupancy_time},{capacity}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              """This method is called once all the FME Features have been processed
              from input().
              """
              self.accumulated_data = self.accumulated_data[:-3]

              # Create a new output feature with accumulated data
              out_feature = fmeobjects.FMEFeature()
              out_feature.setAttribute('accumulated_data', self.accumulated_data.strip())  # Remove trailing space
              self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewStats_UnivWstBlvd [INITIATOR]
WriteNewStats_UnivWstBlvd: SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      ;WITH UniqueSource AS (
          SELECT   week_start_date,
                   week_end_date,
                   zone_id,
                   average_occupancy,
                   peak_occupancy,
                   peak_occupancy_time,
                   Capacity
          FROM (
              SELECT
                   week_start_date,
                   week_end_date,
                   zone_id,
                   average_occupancy,
                   peak_occupancy,
                   peak_occupancy_time,
                   Capacity,
                  ROW_NUMBER() OVER (PARTITION BY week_start_date, zone_id ORDER BY peak_occupancy) AS row_num
              FROM (VALUES
                  @Value(accumulated_data)
              ) AS source( week_start_date,
                           week_end_date,
                           zone_id,
                           average_occupancy,
                           peak_occupancy,
                           peak_occupancy_time,
                           Capacity)
          ) AS ranked
          WHERE row_num = 1
      )



      MERGE INTO [dbo].[Weekly_Occupancy_Stats] AS target
      USING UniqueSource AS source
      ON (target.week_start_date = source.week_start_date AND target.zone_id = source.zone_id)
      WHEN MATCHED THEN
          UPDATE SET
              target.average_occupancy = source.average_occupancy,
              target.peak_occupancy = source.peak_occupancy,
              target.peak_occupancy_time = source.peak_occupancy_time
      WHEN NOT MATCHED THEN
          INSERT ( week_start_date,
                   week_end_date,
                   zone_id,
                   average_occupancy,
                   peak_occupancy,
                   peak_occupancy_time,
                   Capacity )
          VALUES ( source.week_start_date,
                   source.week_end_date,
                   source.zone_id,
                   source.average_occupancy,
                   source.peak_occupancy,
                   source.peak_occupancy_time,
                   source.Capacity);
Thunderbird: Tester
    BOOL_OP = OR
    TEST_CLAUSE = TEST @Value(parkade_name) = Thunderbird Parkade
    TEST_MODE = TEST
    PASSED -> GetLatestDayStatsThunderbird [INITIATOR]
GetLatestDayStatsThunderbird: SQLExecutor
    ATTR_IGNORE_NULLS = Yes
    COMBINE_ATTRS = Keep Initiator Attributes if Conflict
    COMBINE_GEOM = Initiator Geometry Only
    DATASET = AWS_UBCParking
    EXPOSED_ATTRIBUTE_LIST = week_start_date,zone_id
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      SELECT TOP 1 *
      FROM [Parking].[dbo].[Weekly_Occupancy_Stats]
      WHERE zone_id = '@Value(zone_id)'
      ORDER BY week_start_date DESC;
    RESULT -> ConvertDayToUnix_3
ConvertDayToUnix_3: PythonCaller
    NEW_ATTRIBUTES = week_start_date week_start_date_unixtimestamp Occupancy_Table_Name zone_id
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              pass

          def input(self, feature):

              # Convert the date string to a datetime object
              date_time = datetime.datetime.strptime(feature.getAttribute('week_start_date'), '%Y-%m-%d')

              # Convert the datetime object to a UNIX timestamp
              unix_timestamp = int(date_time.timestamp())

              print(f"Date: {feature.getAttribute('date')} -> UNIX Timestamp: {unix_timestamp}")

              feature.setAttribute('week_start_date_unixtimestamp', unix_timestamp)

              self.pyoutput(feature)

          def close(self):
              # Dictionary to store timestamps and their corresponding indices

              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> GetAllDataFromLatestDayThunderbird [INITIATOR]
GetAllDataFromLatestDayThunderbird: SQLExecutor
    ATTR_IGNORE_NULLS = Yes
    COMBINE_ATTRS = Keep Result Attributes if Conflict
    COMBINE_GEOM = Initiator Geometry Only
    DATASET = AWS_UBCParking
    EXPOSED_ATTRIBUTE_LIST = zone_id,TimezoneId,Capacity,Vehicles,Violations,ViolationsEnforced,TimestampUTC,Timestamp,TimestampUnix
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 60
    OUTPUT_FEATURES_DISPLAY = Schema and Data Features
    SQL_STATEMENT:
      SELECT DISTINCT *
      FROM @Value(Occupancy_Table_Name)
      WHERE TimestampUnix > @Value(week_start_date_unixtimestamp)
    RESULT -> AddDayHour_3
AddDayHour_3: PythonCaller
    HIDE_ATTRIBUTES = Timestamp TimestampUnix TimestampUTC TimezoneId Violations ViolationsEnforced zone_id
    NEW_ATTRIBUTES = Date hour_minute Vehicles Capacity
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.data = []
              pass

          def input(self, feature):
              # Convert UNIX timestamp to a datetime object
              date_time = datetime.datetime.fromtimestamp(feature.getAttribute('TimestampUnix'))

              # Format the datetime object to a string in yyyy-mm-dd format
              formatted_date = date_time.strftime('%Y-%m-%d')

              # Get the hour and minute from the datetime object
              hour_minute = date_time.strftime('%H:%M')

              feature.setAttribute('Date', formatted_date)
              feature.setAttribute('hour_minute', hour_minute)

              self.data.append(feature)
              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> AddWeek_3
AddWeek_3: PythonCaller
    NEW_ATTRIBUTES = week_start_date week_end_date Date hour_minute Vehicles Capacity zone_id
    PYTHONSOURCE:
      import fme
      import fmeobjects
      import datetime
      import time

      def get_week_bounds(given_date):
          # Ensure given_date is a datetime.date object
          if isinstance(given_date, str):
              given_date = datetime.datetime.strptime(given_date, "%Y-%m-%d").date()
          elif isinstance(given_date, datetime.datetime):
              given_date = given_date.date()

          # Calculate the first and last day of the week
          start_of_week = given_date - datetime.timedelta(days=given_date.weekday())
          end_of_week = start_of_week + datetime.timedelta(days=6)

          return start_of_week, end_of_week

      class FeatureProcessor(object):
          """Template Class Interface:
          When using this class, make sure its name is set as the value of the 'Class
          to Process Features' transformer parameter.
          """

          def __init__(self):
              """Base constructor for class members."""
              pass

          def input(self, feature):
              # Convert UNIX timestamp to a datetime object
              first_date, last_date = get_week_bounds(feature.getAttribute('Date'))

              feature.setAttribute('week_start_date', first_date.strftime('%Y-%m-%d'))
              feature.setAttribute('week_end_date', last_date.strftime('%Y-%m-%d'))

              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CalculateStatsPerWeek_3
CalculateStatsPerWeek_3: PythonCaller
    GROUP_BY = week_start_date
    HIDE_ATTRIBUTES = Date hour_minute Vehicles
    NEW_ATTRIBUTES = Capacity average_occupancy peak_occupancy peak_occupancy_time week_start_date week_end_date zone_id
    PYTHONSOURCE:
      import fme
      import fmeobjects
      import datetime

      def get_week_bounds(given_date):
          # Ensure given_date is a datetime.date object
          if isinstance(given_date, str):
              given_date = datetime.datetime.strptime(given_date, "%Y-%m-%d").date()
          elif isinstance(given_date, datetime.datetime):
              given_date = given_date.date()

          # Calculate the first and last day of the week
          start_of_week = given_date - datetime.timedelta(days=given_date.weekday())
          end_of_week = start_of_week + datetime.timedelta(days=6)

          return start_of_week, end_of_week

      def datetime_to_unixtimestamp(date_str, time_str):
          try:
              # Parse date and time strings
              date_obj = datetime.datetime.strptime(date_str, "%Y-%m-%d").date()
              time_obj = datetime.datetime.strptime(time_str, "%H:%M").time()

              # Combine date and time
              datetime_combined = datetime.datetime.combine(date_obj, time_obj)

              # Convert to Unix timestamp
              unix_timestamp = int(datetime_combined.timestamp())
              return unix_timestamp
          except ValueError:
              return None


      class FeatureProcessor(object):
          """Template Class Interface:
          When using this class, make sure its name is set as the value of the 'Class
          to Process Features' transformer parameter.
          """
          def __init__(self):
              """Base constructor for class members."""
              self.norm_occ = 0
              self.n = 0
              self.average_occupancy = 0
              self.peak_occupancy = 0
              self.peak_occupancy_time = 0
              self.capacity = 0
              self.week_start_day = ""
              self.week_end_day = ""
              self.date = ""
              self.current_week_start_day, week_last_day = get_week_bounds(datetime.date.today())
              self.zone_id = ""
              pass

          def input(self, feature):
              self.zone_id = str(feature.getAttribute('zone_id'))
              self.week_start_date = feature.getAttribute('week_start_date')
              self.week_end_date = feature.getAttribute('week_end_date')

              if datetime.datetime.strptime(str(self.current_week_start_day), "%Y-%m-%d").date() != self.week_start_date:
                  self.norm_occ += feature.getAttribute('Vehicles')
                  self.n += 1
                  self.capacity = feature.getAttribute('Capacity')
                  if(self.peak_occupancy < feature.getAttribute('Vehicles')):
                      self.peak_occupancy = feature.getAttribute('Vehicles')
                      self.peak_occupancy_time = feature.getAttribute('hour_minute')
                      self.date = feature.getAttribute('Date')
                  """This method is called for each FME Feature entering the
                  PythonCaller. If knowledge of all input Features is not required for
                  processing, then the processed Feature can be emitted from this method
                  through self.pyoutput(). Otherwise, the input FME Feature should be
                  cached to a list class member and processed in process_group() when
                  'Group by' attributes(s) are specified, or the close() method.

                  :param fmeobjects.FMEFeature feature: FME Feature entering the
                      transformer.
                  """

          def close(self):
              """This method is called once all the FME Features have been processed
              from input().
              """

              pass

          def process_group(self):
              if datetime.datetime.strptime(str(self.current_week_start_day), "%Y-%m-%d").date() != self.week_start_date:
                  self.average_occupancy = self.norm_occ / self.n
                  out_feature = fmeobjects.FMEFeature()
                  out_feature.setAttribute('average_occupancy', int(self.average_occupancy))
                  out_feature.setAttribute('zone_id', self.zone_id)
                  out_feature.setAttribute('peak_occupancy', self.peak_occupancy)
                  out_feature.setAttribute('peak_occupancy_time', datetime_to_unixtimestamp(str(self.date), str(self.peak_occupancy_time)))
                  out_feature.setAttribute('Capacity', self.capacity)
                  out_feature.setAttribute('week_start_date', self.week_start_date)
                  out_feature.setAttribute('week_end_date', self.week_end_date)
                  self.pyoutput(out_feature)
                  self.peak_occupancy = 0
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CreateSQL_Thunderbird
CreateSQL_Thunderbird: PythonCaller
    HIDE_ATTRIBUTES = average_occupancy Capacity week_start_date week_end_date peak_occupancy peak_occupancy_time
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              average_occupancy = feature.getAttribute('average_occupancy')
              capacity = feature.getAttribute('Capacity')
              week_start_date = feature.getAttribute('week_start_date')
              week_end_date = feature.getAttribute('week_end_date')
              peak_occupancy = feature.getAttribute('peak_occupancy')
              peak_occupancy_time = feature.getAttribute('peak_occupancy_time')
              zone_id = feature.getAttribute('zone_id')


              # Concatenate the attributes into a single string
              feature_string = f"'{week_start_date}','{week_end_date}','{zone_id}',{average_occupancy},{peak_occupancy},{peak_occupancy_time},{capacity}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              """This method is called once all the FME Features have been processed
              from input().
              """
              self.accumulated_data = self.accumulated_data[:-3]

              # Create a new output feature with accumulated data
              out_feature = fmeobjects.FMEFeature()
              out_feature.setAttribute('accumulated_data', self.accumulated_data.strip())  # Remove trailing space
              self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewStats_Thunderbird [INITIATOR]
WriteNewStats_Thunderbird: SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      ;WITH UniqueSource AS (
          SELECT   week_start_date,
                   week_end_date,
                   zone_id,
                   average_occupancy,
                   peak_occupancy,
                   peak_occupancy_time,
                   Capacity
          FROM (
              SELECT
                   week_start_date,
                   week_end_date,
                   zone_id,
                   average_occupancy,
                   peak_occupancy,
                   peak_occupancy_time,
                   Capacity,
                  ROW_NUMBER() OVER (PARTITION BY week_start_date, zone_id ORDER BY peak_occupancy) AS row_num
              FROM (VALUES
                  @Value(accumulated_data)
              ) AS source( week_start_date,
                           week_end_date,
                           zone_id,
                           average_occupancy,
                           peak_occupancy,
                           peak_occupancy_time,
                           Capacity)
          ) AS ranked
          WHERE row_num = 1
      )



      MERGE INTO [dbo].[Weekly_Occupancy_Stats] AS target
      USING UniqueSource AS source
      ON (target.week_start_date = source.week_start_date AND target.zone_id = source.zone_id)
      WHEN MATCHED THEN
          UPDATE SET
              target.average_occupancy = source.average_occupancy,
              target.peak_occupancy = source.peak_occupancy,
              target.peak_occupancy_time = source.peak_occupancy_time
      WHEN NOT MATCHED THEN
          INSERT ( week_start_date,
                   week_end_date,
                   zone_id,
                   average_occupancy,
                   peak_occupancy,
                   peak_occupancy_time,
                   Capacity )
          VALUES ( source.week_start_date,
                   source.week_end_date,
                   source.zone_id,
                   source.average_occupancy,
                   source.peak_occupancy,
                   source.peak_occupancy_time,
                   source.Capacity);
RoseGarden: Tester
    BOOL_OP = OR
    TEST_CLAUSE = TEST @Value(parkade_name) = Rose Garden Parkade
    TEST_MODE = TEST
    PASSED -> GetLatestDayStatsRoseGarden [INITIATOR]
GetLatestDayStatsRoseGarden: SQLExecutor
    ATTR_IGNORE_NULLS = Yes
    COMBINE_ATTRS = Keep Initiator Attributes if Conflict
    COMBINE_GEOM = Initiator Geometry Only
    DATASET = AWS_UBCParking
    EXPOSED_ATTRIBUTE_LIST = week_start_date,zone_id
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      SELECT TOP 1 *
      FROM [Parking].[dbo].[Weekly_Occupancy_Stats]
      WHERE zone_id = '@Value(zone_id)'
      ORDER BY week_start_date DESC;
    RESULT -> ConvertDayToUnix_4
ConvertDayToUnix_4: PythonCaller
    NEW_ATTRIBUTES = week_start_date week_start_date_unixtimestamp Occupancy_Table_Name zone_id
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              pass

          def input(self, feature):

              # Convert the date string to a datetime object
              date_time = datetime.datetime.strptime(feature.getAttribute('week_start_date'), '%Y-%m-%d')

              # Convert the datetime object to a UNIX timestamp
              unix_timestamp = int(date_time.timestamp())

              print(f"Date: {feature.getAttribute('date')} -> UNIX Timestamp: {unix_timestamp}")

              feature.setAttribute('week_start_date_unixtimestamp', unix_timestamp)

              self.pyoutput(feature)

          def close(self):
              # Dictionary to store timestamps and their corresponding indices

              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> GetAllDataFromLatestDayRoseGarden [INITIATOR]
GetAllDataFromLatestDayRoseGarden: SQLExecutor
    ATTR_IGNORE_NULLS = Yes
    COMBINE_ATTRS = Keep Result Attributes if Conflict
    COMBINE_GEOM = Initiator Geometry Only
    DATASET = AWS_UBCParking
    EXPOSED_ATTRIBUTE_LIST = zone_id,TimezoneId,Capacity,Vehicles,Violations,ViolationsEnforced,TimestampUTC,Timestamp,TimestampUnix
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 60
    OUTPUT_FEATURES_DISPLAY = Schema and Data Features
    SQL_STATEMENT:
      SELECT DISTINCT *
      FROM @Value(Occupancy_Table_Name)
      WHERE TimestampUnix > @Value(week_start_date_unixtimestamp)
    RESULT -> AddDayHour_4
AddDayHour_4: PythonCaller
    HIDE_ATTRIBUTES = Timestamp TimestampUnix TimestampUTC TimezoneId Violations ViolationsEnforced zone_id
    NEW_ATTRIBUTES = Date hour_minute Vehicles Capacity
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.data = []
              pass

          def input(self, feature):
              # Convert UNIX timestamp to a datetime object
              date_time = datetime.datetime.fromtimestamp(feature.getAttribute('TimestampUnix'))

              # Format the datetime object to a string in yyyy-mm-dd format
              formatted_date = date_time.strftime('%Y-%m-%d')

              # Get the hour and minute from the datetime object
              hour_minute = date_time.strftime('%H:%M')

              feature.setAttribute('Date', formatted_date)
              feature.setAttribute('hour_minute', hour_minute)

              self.data.append(feature)
              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> AddWeek_4
AddWeek_4: PythonCaller
    NEW_ATTRIBUTES = week_start_date week_end_date Date hour_minute Vehicles Capacity zone_id
    PYTHONSOURCE:
      import fme
      import fmeobjects
      import datetime
      import time

      def get_week_bounds(given_date):
          # Ensure given_date is a datetime.date object
          if isinstance(given_date, str):
              given_date = datetime.datetime.strptime(given_date, "%Y-%m-%d").date()
          elif isinstance(given_date, datetime.datetime):
              given_date = given_date.date()

          # Calculate the first and last day of the week
          start_of_week = given_date - datetime.timedelta(days=given_date.weekday())
          end_of_week = start_of_week + datetime.timedelta(days=6)

          return start_of_week, end_of_week

      class FeatureProcessor(object):
          """Template Class Interface:
          When using this class, make sure its name is set as the value of the 'Class
          to Process Features' transformer parameter.
          """

          def __init__(self):
              """Base constructor for class members."""
              pass

          def input(self, feature):
              # Convert UNIX timestamp to a datetime object
              first_date, last_date = get_week_bounds(feature.getAttribute('Date'))

              feature.setAttribute('week_start_date', first_date.strftime('%Y-%m-%d'))
              feature.setAttribute('week_end_date', last_date.strftime('%Y-%m-%d'))

              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CalculateStatsPerWeek_4
CalculateStatsPerWeek_4: PythonCaller
    GROUP_BY = week_start_date
    HIDE_ATTRIBUTES = Date hour_minute Vehicles
    NEW_ATTRIBUTES = Capacity average_occupancy peak_occupancy peak_occupancy_time week_start_date week_end_date zone_id
    PYTHONSOURCE:
      import fme
      import fmeobjects
      import datetime

      def get_week_bounds(given_date):
          # Ensure given_date is a datetime.date object
          if isinstance(given_date, str):
              given_date = datetime.datetime.strptime(given_date, "%Y-%m-%d").date()
          elif isinstance(given_date, datetime.datetime):
              given_date = given_date.date()

          # Calculate the first and last day of the week
          start_of_week = given_date - datetime.timedelta(days=given_date.weekday())
          end_of_week = start_of_week + datetime.timedelta(days=6)

          return start_of_week, end_of_week

      def datetime_to_unixtimestamp(date_str, time_str):
          try:
              # Parse date and time strings
              date_obj = datetime.datetime.strptime(date_str, "%Y-%m-%d").date()
              time_obj = datetime.datetime.strptime(time_str, "%H:%M").time()

              # Combine date and time
              datetime_combined = datetime.datetime.combine(date_obj, time_obj)

              # Convert to Unix timestamp
              unix_timestamp = int(datetime_combined.timestamp())
              return unix_timestamp
          except ValueError:
              return None


      class FeatureProcessor(object):
          """Template Class Interface:
          When using this class, make sure its name is set as the value of the 'Class
          to Process Features' transformer parameter.
          """
          def __init__(self):
              """Base constructor for class members."""
              self.norm_occ = 0
              self.n = 0
              self.average_occupancy = 0
              self.peak_occupancy = 0
              self.peak_occupancy_time = 0
              self.capacity = 0
              self.week_start_day = ""
              self.week_end_day = ""
              self.date = ""
              self.current_week_start_day, week_last_day = get_week_bounds(datetime.date.today())
              self.zone_id = ""
              pass

          def input(self, feature):
              self.zone_id = str(feature.getAttribute('zone_id'))
              self.week_start_date = feature.getAttribute('week_start_date')
              self.week_end_date = feature.getAttribute('week_end_date')

              if datetime.datetime.strptime(str(self.current_week_start_day), "%Y-%m-%d").date() != self.week_start_date:
                  self.norm_occ += feature.getAttribute('Vehicles')
                  self.n += 1
                  self.capacity = feature.getAttribute('Capacity')
                  if(self.peak_occupancy < feature.getAttribute('Vehicles')):
                      self.peak_occupancy = feature.getAttribute('Vehicles')
                      self.peak_occupancy_time = feature.getAttribute('hour_minute')
                      self.date = feature.getAttribute('Date')
                  """This method is called for each FME Feature entering the
                  PythonCaller. If knowledge of all input Features is not required for
                  processing, then the processed Feature can be emitted from this method
                  through self.pyoutput(). Otherwise, the input FME Feature should be
                  cached to a list class member and processed in process_group() when
                  'Group by' attributes(s) are specified, or the close() method.

                  :param fmeobjects.FMEFeature feature: FME Feature entering the
                      transformer.
                  """

          def close(self):
              """This method is called once all the FME Features have been processed
              from input().
              """

              pass

          def process_group(self):
              if datetime.datetime.strptime(str(self.current_week_start_day), "%Y-%m-%d").date() != self.week_start_date:
                  self.average_occupancy = self.norm_occ / self.n
                  out_feature = fmeobjects.FMEFeature()
                  out_feature.setAttribute('average_occupancy', int(self.average_occupancy))
                  out_feature.setAttribute('zone_id', self.zone_id)
                  out_feature.setAttribute('peak_occupancy', self.peak_occupancy)
                  out_feature.setAttribute('peak_occupancy_time', datetime_to_unixtimestamp(str(self.date), str(self.peak_occupancy_time)))
                  out_feature.setAttribute('Capacity', self.capacity)
                  out_feature.setAttribute('week_start_date', self.week_start_date)
                  out_feature.setAttribute('week_end_date', self.week_end_date)
                  self.pyoutput(out_feature)
                  self.peak_occupancy = 0
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CreateSQL_RoseGarden
CreateSQL_RoseGarden: PythonCaller
    HIDE_ATTRIBUTES = average_occupancy Capacity week_start_date week_end_date peak_occupancy peak_occupancy_time
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              average_occupancy = feature.getAttribute('average_occupancy')
              capacity = feature.getAttribute('Capacity')
              week_start_date = feature.getAttribute('week_start_date')
              week_end_date = feature.getAttribute('week_end_date')
              peak_occupancy = feature.getAttribute('peak_occupancy')
              peak_occupancy_time = feature.getAttribute('peak_occupancy_time')
              zone_id = feature.getAttribute('zone_id')


              # Concatenate the attributes into a single string
              feature_string = f"'{week_start_date}','{week_end_date}','{zone_id}',{average_occupancy},{peak_occupancy},{peak_occupancy_time},{capacity}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              """This method is called once all the FME Features have been processed
              from input().
              """
              self.accumulated_data = self.accumulated_data[:-3]

              # Create a new output feature with accumulated data
              out_feature = fmeobjects.FMEFeature()
              out_feature.setAttribute('accumulated_data', self.accumulated_data.strip())  # Remove trailing space
              self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewStats_RoseGarden [INITIATOR]
WriteNewStats_RoseGarden: SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      ;WITH UniqueSource AS (
          SELECT   week_start_date,
                   week_end_date,
                   zone_id,
                   average_occupancy,
                   peak_occupancy,
                   peak_occupancy_time,
                   Capacity
          FROM (
              SELECT
                   week_start_date,
                   week_end_date,
                   zone_id,
                   average_occupancy,
                   peak_occupancy,
                   peak_occupancy_time,
                   Capacity,
                  ROW_NUMBER() OVER (PARTITION BY week_start_date, zone_id ORDER BY peak_occupancy) AS row_num
              FROM (VALUES
                  @Value(accumulated_data)
              ) AS source( week_start_date,
                           week_end_date,
                           zone_id,
                           average_occupancy,
                           peak_occupancy,
                           peak_occupancy_time,
                           Capacity)
          ) AS ranked
          WHERE row_num = 1
      )



      MERGE INTO [dbo].[Weekly_Occupancy_Stats] AS target
      USING UniqueSource AS source
      ON (target.week_start_date = source.week_start_date AND target.zone_id = source.zone_id)
      WHEN MATCHED THEN
          UPDATE SET
              target.average_occupancy = source.average_occupancy,
              target.peak_occupancy = source.peak_occupancy,
              target.peak_occupancy_time = source.peak_occupancy_time
      WHEN NOT MATCHED THEN
          INSERT ( week_start_date,
                   week_end_date,
                   zone_id,
                   average_occupancy,
                   peak_occupancy,
                   peak_occupancy_time,
                   Capacity )
          VALUES ( source.week_start_date,
                   source.week_end_date,
                   source.zone_id,
                   source.average_occupancy,
                   source.peak_occupancy,
                   source.peak_occupancy_time,
                   source.Capacity);
North: Tester
    BOOL_OP = OR
    TEST_CLAUSE = TEST @Value(parkade_name) = North Parkade
    TEST_MODE = TEST
    PASSED -> GetLatestDayStatsNorth [INITIATOR]
GetLatestDayStatsNorth: SQLExecutor
    ATTR_IGNORE_NULLS = Yes
    COMBINE_ATTRS = Keep Initiator Attributes if Conflict
    COMBINE_GEOM = Initiator Geometry Only
    DATASET = AWS_UBCParking
    EXPOSED_ATTRIBUTE_LIST = week_start_date,zone_id
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      SELECT TOP 1 *
      FROM [Parking].[dbo].[Weekly_Occupancy_Stats]
      WHERE zone_id = '@Value(zone_id)'
      ORDER BY week_start_date DESC;
    RESULT -> ConvertDayToUnix_5
ConvertDayToUnix_5: PythonCaller
    NEW_ATTRIBUTES = week_start_date week_start_date_unixtimestamp Occupancy_Table_Name zone_id
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              pass

          def input(self, feature):

              # Convert the date string to a datetime object
              date_time = datetime.datetime.strptime(feature.getAttribute('week_start_date'), '%Y-%m-%d')

              # Convert the datetime object to a UNIX timestamp
              unix_timestamp = int(date_time.timestamp())

              print(f"Date: {feature.getAttribute('date')} -> UNIX Timestamp: {unix_timestamp}")

              feature.setAttribute('week_start_date_unixtimestamp', unix_timestamp)

              self.pyoutput(feature)

          def close(self):
              # Dictionary to store timestamps and their corresponding indices

              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> GetAllDataFromLatestDayNorth [INITIATOR]
GetAllDataFromLatestDayNorth: SQLExecutor
    ATTR_IGNORE_NULLS = Yes
    COMBINE_ATTRS = Keep Result Attributes if Conflict
    COMBINE_GEOM = Initiator Geometry Only
    DATASET = AWS_UBCParking
    EXPOSED_ATTRIBUTE_LIST = zone_id,TimezoneId,Capacity,Vehicles,Violations,ViolationsEnforced,TimestampUTC,Timestamp,TimestampUnix
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 60
    OUTPUT_FEATURES_DISPLAY = Schema and Data Features
    SQL_STATEMENT:
      SELECT DISTINCT *
      FROM @Value(Occupancy_Table_Name)
      WHERE TimestampUnix > @Value(week_start_date_unixtimestamp)
    RESULT -> AddDayHour_5
AddDayHour_5: PythonCaller
    HIDE_ATTRIBUTES = Timestamp TimestampUnix TimestampUTC TimezoneId Violations ViolationsEnforced zone_id
    NEW_ATTRIBUTES = Date hour_minute Vehicles Capacity
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.data = []
              pass

          def input(self, feature):
              # Convert UNIX timestamp to a datetime object
              date_time = datetime.datetime.fromtimestamp(feature.getAttribute('TimestampUnix'))

              # Format the datetime object to a string in yyyy-mm-dd format
              formatted_date = date_time.strftime('%Y-%m-%d')

              # Get the hour and minute from the datetime object
              hour_minute = date_time.strftime('%H:%M')

              feature.setAttribute('Date', formatted_date)
              feature.setAttribute('hour_minute', hour_minute)

              self.data.append(feature)
              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> AddWeek_5
AddWeek_5: PythonCaller
    NEW_ATTRIBUTES = week_start_date week_end_date Date hour_minute Vehicles Capacity zone_id
    PYTHONSOURCE:
      import fme
      import fmeobjects
      import datetime
      import time

      def get_week_bounds(given_date):
          # Ensure given_date is a datetime.date object
          if isinstance(given_date, str):
              given_date = datetime.datetime.strptime(given_date, "%Y-%m-%d").date()
          elif isinstance(given_date, datetime.datetime):
              given_date = given_date.date()

          # Calculate the first and last day of the week
          start_of_week = given_date - datetime.timedelta(days=given_date.weekday())
          end_of_week = start_of_week + datetime.timedelta(days=6)

          return start_of_week, end_of_week

      class FeatureProcessor(object):
          """Template Class Interface:
          When using this class, make sure its name is set as the value of the 'Class
          to Process Features' transformer parameter.
          """

          def __init__(self):
              """Base constructor for class members."""
              pass

          def input(self, feature):
              # Convert UNIX timestamp to a datetime object
              first_date, last_date = get_week_bounds(feature.getAttribute('Date'))

              feature.setAttribute('week_start_date', first_date.strftime('%Y-%m-%d'))
              feature.setAttribute('week_end_date', last_date.strftime('%Y-%m-%d'))

              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CalculateStatsPerWeek_5
CalculateStatsPerWeek_5: PythonCaller
    GROUP_BY = week_start_date
    HIDE_ATTRIBUTES = Date hour_minute Vehicles
    NEW_ATTRIBUTES = Capacity average_occupancy peak_occupancy peak_occupancy_time week_start_date week_end_date zone_id
    PYTHONSOURCE:
      import fme
      import fmeobjects
      import datetime

      def get_week_bounds(given_date):
          # Ensure given_date is a datetime.date object
          if isinstance(given_date, str):
              given_date = datetime.datetime.strptime(given_date, "%Y-%m-%d").date()
          elif isinstance(given_date, datetime.datetime):
              given_date = given_date.date()

          # Calculate the first and last day of the week
          start_of_week = given_date - datetime.timedelta(days=given_date.weekday())
          end_of_week = start_of_week + datetime.timedelta(days=6)

          return start_of_week, end_of_week

      def datetime_to_unixtimestamp(date_str, time_str):
          try:
              # Parse date and time strings
              date_obj = datetime.datetime.strptime(date_str, "%Y-%m-%d").date()
              time_obj = datetime.datetime.strptime(time_str, "%H:%M").time()

              # Combine date and time
              datetime_combined = datetime.datetime.combine(date_obj, time_obj)

              # Convert to Unix timestamp
              unix_timestamp = int(datetime_combined.timestamp())
              return unix_timestamp
          except ValueError:
              return None


      class FeatureProcessor(object):
          """Template Class Interface:
          When using this class, make sure its name is set as the value of the 'Class
          to Process Features' transformer parameter.
          """
          def __init__(self):
              """Base constructor for class members."""
              self.norm_occ = 0
              self.n = 0
              self.average_occupancy = 0
              self.peak_occupancy = 0
              self.peak_occupancy_time = 0
              self.capacity = 0
              self.week_start_day = ""
              self.week_end_day = ""
              self.date = ""
              self.current_week_start_day, week_last_day = get_week_bounds(datetime.date.today())
              self.zone_id = ""
              pass

          def input(self, feature):
              self.zone_id = str(feature.getAttribute('zone_id'))
              self.week_start_date = feature.getAttribute('week_start_date')
              self.week_end_date = feature.getAttribute('week_end_date')

              if datetime.datetime.strptime(str(self.current_week_start_day), "%Y-%m-%d").date() != self.week_start_date:
                  self.norm_occ += feature.getAttribute('Vehicles')
                  self.n += 1
                  self.capacity = feature.getAttribute('Capacity')
                  if(self.peak_occupancy < feature.getAttribute('Vehicles')):
                      self.peak_occupancy = feature.getAttribute('Vehicles')
                      self.peak_occupancy_time = feature.getAttribute('hour_minute')
                      self.date = feature.getAttribute('Date')
                  """This method is called for each FME Feature entering the
                  PythonCaller. If knowledge of all input Features is not required for
                  processing, then the processed Feature can be emitted from this method
                  through self.pyoutput(). Otherwise, the input FME Feature should be
                  cached to a list class member and processed in process_group() when
                  'Group by' attributes(s) are specified, or the close() method.

                  :param fmeobjects.FMEFeature feature: FME Feature entering the
                      transformer.
                  """

          def close(self):
              """This method is called once all the FME Features have been processed
              from input().
              """

              pass

          def process_group(self):
              if datetime.datetime.strptime(str(self.current_week_start_day), "%Y-%m-%d").date() != self.week_start_date:
                  self.average_occupancy = self.norm_occ / self.n
                  out_feature = fmeobjects.FMEFeature()
                  out_feature.setAttribute('average_occupancy', int(self.average_occupancy))
                  out_feature.setAttribute('zone_id', self.zone_id)
                  out_feature.setAttribute('peak_occupancy', self.peak_occupancy)
                  out_feature.setAttribute('peak_occupancy_time', datetime_to_unixtimestamp(str(self.date), str(self.peak_occupancy_time)))
                  out_feature.setAttribute('Capacity', self.capacity)
                  out_feature.setAttribute('week_start_date', self.week_start_date)
                  out_feature.setAttribute('week_end_date', self.week_end_date)
                  self.pyoutput(out_feature)
                  self.peak_occupancy = 0
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CreateSQL_North
CreateSQL_North: PythonCaller
    HIDE_ATTRIBUTES = average_occupancy Capacity week_start_date week_end_date peak_occupancy peak_occupancy_time
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              average_occupancy = feature.getAttribute('average_occupancy')
              capacity = feature.getAttribute('Capacity')
              week_start_date = feature.getAttribute('week_start_date')
              week_end_date = feature.getAttribute('week_end_date')
              peak_occupancy = feature.getAttribute('peak_occupancy')
              peak_occupancy_time = feature.getAttribute('peak_occupancy_time')
              zone_id = feature.getAttribute('zone_id')


              # Concatenate the attributes into a single string
              feature_string = f"'{week_start_date}','{week_end_date}','{zone_id}',{average_occupancy},{peak_occupancy},{peak_occupancy_time},{capacity}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              """This method is called once all the FME Features have been processed
              from input().
              """
              self.accumulated_data = self.accumulated_data[:-3]

              # Create a new output feature with accumulated data
              out_feature = fmeobjects.FMEFeature()
              out_feature.setAttribute('accumulated_data', self.accumulated_data.strip())  # Remove trailing space
              self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewStats_North [INITIATOR]
WriteNewStats_North: SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      ;WITH UniqueSource AS (
          SELECT   week_start_date,
                   week_end_date,
                   zone_id,
                   average_occupancy,
                   peak_occupancy,
                   peak_occupancy_time,
                   Capacity
          FROM (
              SELECT
                   week_start_date,
                   week_end_date,
                   zone_id,
                   average_occupancy,
                   peak_occupancy,
                   peak_occupancy_time,
                   Capacity,
                  ROW_NUMBER() OVER (PARTITION BY week_start_date, zone_id ORDER BY peak_occupancy) AS row_num
              FROM (VALUES
                  @Value(accumulated_data)
              ) AS source( week_start_date,
                           week_end_date,
                           zone_id,
                           average_occupancy,
                           peak_occupancy,
                           peak_occupancy_time,
                           Capacity)
          ) AS ranked
          WHERE row_num = 1
      )



      MERGE INTO [dbo].[Weekly_Occupancy_Stats] AS target
      USING UniqueSource AS source
      ON (target.week_start_date = source.week_start_date AND target.zone_id = source.zone_id)
      WHEN MATCHED THEN
          UPDATE SET
              target.average_occupancy = source.average_occupancy,
              target.peak_occupancy = source.peak_occupancy,
              target.peak_occupancy_time = source.peak_occupancy_time
      WHEN NOT MATCHED THEN
          INSERT ( week_start_date,
                   week_end_date,
                   zone_id,
                   average_occupancy,
                   peak_occupancy,
                   peak_occupancy_time,
                   Capacity )
          VALUES ( source.week_start_date,
                   source.week_end_date,
                   source.zone_id,
                   source.average_occupancy,
                   source.peak_occupancy,
                   source.peak_occupancy_time,
                   source.Capacity);
HealthSciences: Tester
    BOOL_OP = OR
    TEST_CLAUSE = TEST @Value(parkade_name) = Health Sciences Parkade
    TEST_MODE = TEST
    PASSED -> GetLatestDayStatsHealthSciences [INITIATOR]
GetLatestDayStatsHealthSciences: SQLExecutor
    ATTR_IGNORE_NULLS = Yes
    COMBINE_ATTRS = Keep Initiator Attributes if Conflict
    COMBINE_GEOM = Initiator Geometry Only
    DATASET = AWS_UBCParking
    EXPOSED_ATTRIBUTE_LIST = week_start_date,zone_id
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      SELECT TOP 1 *
      FROM [Parking].[dbo].[Weekly_Occupancy_Stats]
      WHERE zone_id = '@Value(zone_id)'
      ORDER BY week_start_date DESC;
    RESULT -> ConvertDayToUnix_6
ConvertDayToUnix_6: PythonCaller
    NEW_ATTRIBUTES = week_start_date week_start_date_unixtimestamp Occupancy_Table_Name zone_id
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              pass

          def input(self, feature):

              # Convert the date string to a datetime object
              date_time = datetime.datetime.strptime(feature.getAttribute('week_start_date'), '%Y-%m-%d')

              # Convert the datetime object to a UNIX timestamp
              unix_timestamp = int(date_time.timestamp())

              print(f"Date: {feature.getAttribute('date')} -> UNIX Timestamp: {unix_timestamp}")

              feature.setAttribute('week_start_date_unixtimestamp', unix_timestamp)

              self.pyoutput(feature)

          def close(self):
              # Dictionary to store timestamps and their corresponding indices

              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> GetAllDataFromLatestDayHealthSciences [INITIATOR]
GetAllDataFromLatestDayHealthSciences: SQLExecutor
    ATTR_IGNORE_NULLS = Yes
    COMBINE_ATTRS = Keep Result Attributes if Conflict
    COMBINE_GEOM = Initiator Geometry Only
    DATASET = AWS_UBCParking
    EXPOSED_ATTRIBUTE_LIST = zone_id,TimezoneId,Capacity,Vehicles,Violations,ViolationsEnforced,TimestampUTC,Timestamp,TimestampUnix
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 60
    OUTPUT_FEATURES_DISPLAY = Schema and Data Features
    SQL_STATEMENT:
      SELECT DISTINCT *
      FROM @Value(Occupancy_Table_Name)
      WHERE TimestampUnix > @Value(week_start_date_unixtimestamp)
    RESULT -> AddDayHour_6
AddDayHour_6: PythonCaller
    HIDE_ATTRIBUTES = Timestamp TimestampUnix TimestampUTC TimezoneId Violations ViolationsEnforced zone_id
    NEW_ATTRIBUTES = Date hour_minute Vehicles Capacity
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.data = []
              pass

          def input(self, feature):
              # Convert UNIX timestamp to a datetime object
              date_time = datetime.datetime.fromtimestamp(feature.getAttribute('TimestampUnix'))

              # Format the datetime object to a string in yyyy-mm-dd format
              formatted_date = date_time.strftime('%Y-%m-%d')

              # Get the hour and minute from the datetime object
              hour_minute = date_time.strftime('%H:%M')

              feature.setAttribute('Date', formatted_date)
              feature.setAttribute('hour_minute', hour_minute)

              self.data.append(feature)
              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> AddWeek_6
AddWeek_6: PythonCaller
    NEW_ATTRIBUTES = week_start_date week_end_date Date hour_minute Vehicles Capacity zone_id
    PYTHONSOURCE:
      import fme
      import fmeobjects
      import datetime
      import time

      def get_week_bounds(given_date):
          # Ensure given_date is a datetime.date object
          if isinstance(given_date, str):
              given_date = datetime.datetime.strptime(given_date, "%Y-%m-%d").date()
          elif isinstance(given_date, datetime.datetime):
              given_date = given_date.date()

          # Calculate the first and last day of the week
          start_of_week = given_date - datetime.timedelta(days=given_date.weekday())
          end_of_week = start_of_week + datetime.timedelta(days=6)

          return start_of_week, end_of_week

      class FeatureProcessor(object):
          """Template Class Interface:
          When using this class, make sure its name is set as the value of the 'Class
          to Process Features' transformer parameter.
          """

          def __init__(self):
              """Base constructor for class members."""
              pass

          def input(self, feature):
              # Convert UNIX timestamp to a datetime object
              first_date, last_date = get_week_bounds(feature.getAttribute('Date'))

              feature.setAttribute('week_start_date', first_date.strftime('%Y-%m-%d'))
              feature.setAttribute('week_end_date', last_date.strftime('%Y-%m-%d'))

              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CalculateStatsPerWeek_6
CalculateStatsPerWeek_6: PythonCaller
    GROUP_BY = week_start_date
    HIDE_ATTRIBUTES = Date hour_minute Vehicles
    NEW_ATTRIBUTES = Capacity average_occupancy peak_occupancy peak_occupancy_time week_start_date week_end_date zone_id
    PYTHONSOURCE:
      import fme
      import fmeobjects
      import datetime

      def get_week_bounds(given_date):
          # Ensure given_date is a datetime.date object
          if isinstance(given_date, str):
              given_date = datetime.datetime.strptime(given_date, "%Y-%m-%d").date()
          elif isinstance(given_date, datetime.datetime):
              given_date = given_date.date()

          # Calculate the first and last day of the week
          start_of_week = given_date - datetime.timedelta(days=given_date.weekday())
          end_of_week = start_of_week + datetime.timedelta(days=6)

          return start_of_week, end_of_week

      def datetime_to_unixtimestamp(date_str, time_str):
          try:
              # Parse date and time strings
              date_obj = datetime.datetime.strptime(date_str, "%Y-%m-%d").date()
              time_obj = datetime.datetime.strptime(time_str, "%H:%M").time()

              # Combine date and time
              datetime_combined = datetime.datetime.combine(date_obj, time_obj)

              # Convert to Unix timestamp
              unix_timestamp = int(datetime_combined.timestamp())
              return unix_timestamp
          except ValueError:
              return None


      class FeatureProcessor(object):
          """Template Class Interface:
          When using this class, make sure its name is set as the value of the 'Class
          to Process Features' transformer parameter.
          """
          def __init__(self):
              """Base constructor for class members."""
              self.norm_occ = 0
              self.n = 0
              self.average_occupancy = 0
              self.peak_occupancy = 0
              self.peak_occupancy_time = 0
              self.capacity = 0
              self.week_start_day = ""
              self.week_end_day = ""
              self.date = ""
              self.current_week_start_day, week_last_day = get_week_bounds(datetime.date.today())
              self.zone_id = ""
              pass

          def input(self, feature):
              self.zone_id = str(feature.getAttribute('zone_id'))
              self.week_start_date = feature.getAttribute('week_start_date')
              self.week_end_date = feature.getAttribute('week_end_date')

              if datetime.datetime.strptime(str(self.current_week_start_day), "%Y-%m-%d").date() != self.week_start_date:
                  self.norm_occ += feature.getAttribute('Vehicles')
                  self.n += 1
                  self.capacity = feature.getAttribute('Capacity')
                  if(self.peak_occupancy < feature.getAttribute('Vehicles')):
                      self.peak_occupancy = feature.getAttribute('Vehicles')
                      self.peak_occupancy_time = feature.getAttribute('hour_minute')
                      self.date = feature.getAttribute('Date')
                  """This method is called for each FME Feature entering the
                  PythonCaller. If knowledge of all input Features is not required for
                  processing, then the processed Feature can be emitted from this method
                  through self.pyoutput(). Otherwise, the input FME Feature should be
                  cached to a list class member and processed in process_group() when
                  'Group by' attributes(s) are specified, or the close() method.

                  :param fmeobjects.FMEFeature feature: FME Feature entering the
                      transformer.
                  """

          def close(self):
              """This method is called once all the FME Features have been processed
              from input().
              """

              pass

          def process_group(self):
              if datetime.datetime.strptime(str(self.current_week_start_day), "%Y-%m-%d").date() != self.week_start_date:
                  self.average_occupancy = self.norm_occ / self.n
                  out_feature = fmeobjects.FMEFeature()
                  out_feature.setAttribute('average_occupancy', int(self.average_occupancy))
                  out_feature.setAttribute('zone_id', self.zone_id)
                  out_feature.setAttribute('peak_occupancy', self.peak_occupancy)
                  out_feature.setAttribute('peak_occupancy_time', datetime_to_unixtimestamp(str(self.date), str(self.peak_occupancy_time)))
                  out_feature.setAttribute('Capacity', self.capacity)
                  out_feature.setAttribute('week_start_date', self.week_start_date)
                  out_feature.setAttribute('week_end_date', self.week_end_date)
                  self.pyoutput(out_feature)
                  self.peak_occupancy = 0
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CreateSQL_HealthSciences
CreateSQL_HealthSciences: PythonCaller
    HIDE_ATTRIBUTES = average_occupancy Capacity week_start_date week_end_date peak_occupancy peak_occupancy_time
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              average_occupancy = feature.getAttribute('average_occupancy')
              capacity = feature.getAttribute('Capacity')
              week_start_date = feature.getAttribute('week_start_date')
              week_end_date = feature.getAttribute('week_end_date')
              peak_occupancy = feature.getAttribute('peak_occupancy')
              peak_occupancy_time = feature.getAttribute('peak_occupancy_time')
              zone_id = feature.getAttribute('zone_id')


              # Concatenate the attributes into a single string
              feature_string = f"'{week_start_date}','{week_end_date}','{zone_id}',{average_occupancy},{peak_occupancy},{peak_occupancy_time},{capacity}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              """This method is called once all the FME Features have been processed
              from input().
              """
              self.accumulated_data = self.accumulated_data[:-3]

              # Create a new output feature with accumulated data
              out_feature = fmeobjects.FMEFeature()
              out_feature.setAttribute('accumulated_data', self.accumulated_data.strip())  # Remove trailing space
              self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewStats_HealthSciences [INITIATOR]
WriteNewStats_HealthSciences: SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      ;WITH UniqueSource AS (
          SELECT   week_start_date,
                   week_end_date,
                   zone_id,
                   average_occupancy,
                   peak_occupancy,
                   peak_occupancy_time,
                   Capacity
          FROM (
              SELECT
                   week_start_date,
                   week_end_date,
                   zone_id,
                   average_occupancy,
                   peak_occupancy,
                   peak_occupancy_time,
                   Capacity,
                  ROW_NUMBER() OVER (PARTITION BY week_start_date, zone_id ORDER BY peak_occupancy) AS row_num
              FROM (VALUES
                  @Value(accumulated_data)
              ) AS source( week_start_date,
                           week_end_date,
                           zone_id,
                           average_occupancy,
                           peak_occupancy,
                           peak_occupancy_time,
                           Capacity)
          ) AS ranked
          WHERE row_num = 1
      )



      MERGE INTO [dbo].[Weekly_Occupancy_Stats] AS target
      USING UniqueSource AS source
      ON (target.week_start_date = source.week_start_date AND target.zone_id = source.zone_id)
      WHEN MATCHED THEN
          UPDATE SET
              target.average_occupancy = source.average_occupancy,
              target.peak_occupancy = source.peak_occupancy,
              target.peak_occupancy_time = source.peak_occupancy_time
      WHEN NOT MATCHED THEN
          INSERT ( week_start_date,
                   week_end_date,
                   zone_id,
                   average_occupancy,
                   peak_occupancy,
                   peak_occupancy_time,
                   Capacity )
          VALUES ( source.week_start_date,
                   source.week_end_date,
                   source.zone_id,
                   source.average_occupancy,
                   source.peak_occupancy,
                   source.peak_occupancy_time,
                   source.Capacity);
Fraser: Tester
    BOOL_OP = OR
    TEST_CLAUSE = TEST @Value(parkade_name) = Fraser Parkade
    TEST_MODE = TEST
    PASSED -> GetLatestDayStatsFraser [INITIATOR]
GetLatestDayStatsFraser: SQLExecutor
    ATTR_IGNORE_NULLS = Yes
    COMBINE_ATTRS = Keep Initiator Attributes if Conflict
    COMBINE_GEOM = Initiator Geometry Only
    DATASET = AWS_UBCParking
    EXPOSED_ATTRIBUTE_LIST = week_start_date,zone_id
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      SELECT TOP 1 *
      FROM [Parking].[dbo].[Weekly_Occupancy_Stats]
      WHERE zone_id = '@Value(zone_id)'
      ORDER BY week_start_date DESC;
    RESULT -> ConvertDayToUnix_7
ConvertDayToUnix_7: PythonCaller
    NEW_ATTRIBUTES = week_start_date week_start_date_unixtimestamp Occupancy_Table_Name zone_id
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              pass

          def input(self, feature):

              # Convert the date string to a datetime object
              date_time = datetime.datetime.strptime(feature.getAttribute('week_start_date'), '%Y-%m-%d')

              # Convert the datetime object to a UNIX timestamp
              unix_timestamp = int(date_time.timestamp())

              print(f"Date: {feature.getAttribute('date')} -> UNIX Timestamp: {unix_timestamp}")

              feature.setAttribute('week_start_date_unixtimestamp', unix_timestamp)

              self.pyoutput(feature)

          def close(self):
              # Dictionary to store timestamps and their corresponding indices

              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> GetAllDataFromLatestDayFraser [INITIATOR]
GetAllDataFromLatestDayFraser: SQLExecutor
    ATTR_IGNORE_NULLS = Yes
    COMBINE_ATTRS = Keep Result Attributes if Conflict
    COMBINE_GEOM = Initiator Geometry Only
    DATASET = AWS_UBCParking
    EXPOSED_ATTRIBUTE_LIST = zone_id,TimezoneId,Capacity,Vehicles,Violations,ViolationsEnforced,TimestampUTC,Timestamp,TimestampUnix
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 60
    OUTPUT_FEATURES_DISPLAY = Schema and Data Features
    SQL_STATEMENT:
      SELECT DISTINCT *
      FROM @Value(Occupancy_Table_Name)
      WHERE TimestampUnix > @Value(week_start_date_unixtimestamp)
    RESULT -> AddDayHour_7
AddDayHour_7: PythonCaller
    HIDE_ATTRIBUTES = Timestamp TimestampUnix TimestampUTC TimezoneId Violations ViolationsEnforced zone_id
    NEW_ATTRIBUTES = Date hour_minute Vehicles Capacity
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.data = []
              pass

          def input(self, feature):
              # Convert UNIX timestamp to a datetime object
              date_time = datetime.datetime.fromtimestamp(feature.getAttribute('TimestampUnix'))

              # Format the datetime object to a string in yyyy-mm-dd format
              formatted_date = date_time.strftime('%Y-%m-%d')

              # Get the hour and minute from the datetime object
              hour_minute = date_time.strftime('%H:%M')

              feature.setAttribute('Date', formatted_date)
              feature.setAttribute('hour_minute', hour_minute)

              self.data.append(feature)
              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> AddWeek_7
AddWeek_7: PythonCaller
    NEW_ATTRIBUTES = week_start_date week_end_date Date hour_minute Vehicles Capacity zone_id
    PYTHONSOURCE:
      import fme
      import fmeobjects
      import datetime
      import time

      def get_week_bounds(given_date):
          # Ensure given_date is a datetime.date object
          if isinstance(given_date, str):
              given_date = datetime.datetime.strptime(given_date, "%Y-%m-%d").date()
          elif isinstance(given_date, datetime.datetime):
              given_date = given_date.date()

          # Calculate the first and last day of the week
          start_of_week = given_date - datetime.timedelta(days=given_date.weekday())
          end_of_week = start_of_week + datetime.timedelta(days=6)

          return start_of_week, end_of_week

      class FeatureProcessor(object):
          """Template Class Interface:
          When using this class, make sure its name is set as the value of the 'Class
          to Process Features' transformer parameter.
          """

          def __init__(self):
              """Base constructor for class members."""
              pass

          def input(self, feature):
              # Convert UNIX timestamp to a datetime object
              first_date, last_date = get_week_bounds(feature.getAttribute('Date'))

              feature.setAttribute('week_start_date', first_date.strftime('%Y-%m-%d'))
              feature.setAttribute('week_end_date', last_date.strftime('%Y-%m-%d'))

              self.pyoutput(feature)

          def close(self):

              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CalculateStatsPerWeek_7
CalculateStatsPerWeek_7: PythonCaller
    GROUP_BY = week_start_date
    HIDE_ATTRIBUTES = Date hour_minute Vehicles
    NEW_ATTRIBUTES = Capacity average_occupancy peak_occupancy peak_occupancy_time week_start_date week_end_date zone_id
    PYTHONSOURCE:
      import fme
      import fmeobjects
      import datetime

      def get_week_bounds(given_date):
          # Ensure given_date is a datetime.date object
          if isinstance(given_date, str):
              given_date = datetime.datetime.strptime(given_date, "%Y-%m-%d").date()
          elif isinstance(given_date, datetime.datetime):
              given_date = given_date.date()

          # Calculate the first and last day of the week
          start_of_week = given_date - datetime.timedelta(days=given_date.weekday())
          end_of_week = start_of_week + datetime.timedelta(days=6)

          return start_of_week, end_of_week

      def datetime_to_unixtimestamp(date_str, time_str):
          try:
              # Parse date and time strings
              date_obj = datetime.datetime.strptime(date_str, "%Y-%m-%d").date()
              time_obj = datetime.datetime.strptime(time_str, "%H:%M").time()

              # Combine date and time
              datetime_combined = datetime.datetime.combine(date_obj, time_obj)

              # Convert to Unix timestamp
              unix_timestamp = int(datetime_combined.timestamp())
              return unix_timestamp
          except ValueError:
              return None


      class FeatureProcessor(object):
          """Template Class Interface:
          When using this class, make sure its name is set as the value of the 'Class
          to Process Features' transformer parameter.
          """
          def __init__(self):
              """Base constructor for class members."""
              self.norm_occ = 0
              self.n = 0
              self.average_occupancy = 0
              self.peak_occupancy = 0
              self.peak_occupancy_time = 0
              self.capacity = 0
              self.week_start_day = ""
              self.week_end_day = ""
              self.date = ""
              self.current_week_start_day, week_last_day = get_week_bounds(datetime.date.today())
              self.zone_id = ""
              pass

          def input(self, feature):
              self.zone_id = str(feature.getAttribute('zone_id'))
              self.week_start_date = feature.getAttribute('week_start_date')
              self.week_end_date = feature.getAttribute('week_end_date')

              if datetime.datetime.strptime(str(self.current_week_start_day), "%Y-%m-%d").date() != self.week_start_date:
                  self.norm_occ += feature.getAttribute('Vehicles')
                  self.n += 1
                  self.capacity = feature.getAttribute('Capacity')
                  if(self.peak_occupancy < feature.getAttribute('Vehicles')):
                      self.peak_occupancy = feature.getAttribute('Vehicles')
                      self.peak_occupancy_time = feature.getAttribute('hour_minute')
                      self.date = feature.getAttribute('Date')
                  """This method is called for each FME Feature entering the
                  PythonCaller. If knowledge of all input Features is not required for
                  processing, then the processed Feature can be emitted from this method
                  through self.pyoutput(). Otherwise, the input FME Feature should be
                  cached to a list class member and processed in process_group() when
                  'Group by' attributes(s) are specified, or the close() method.

                  :param fmeobjects.FMEFeature feature: FME Feature entering the
                      transformer.
                  """

          def close(self):
              """This method is called once all the FME Features have been processed
              from input().
              """

              pass

          def process_group(self):
              if datetime.datetime.strptime(str(self.current_week_start_day), "%Y-%m-%d").date() != self.week_start_date:
                  self.average_occupancy = self.norm_occ / self.n
                  out_feature = fmeobjects.FMEFeature()
                  out_feature.setAttribute('average_occupancy', int(self.average_occupancy))
                  out_feature.setAttribute('zone_id', self.zone_id)
                  out_feature.setAttribute('peak_occupancy', self.peak_occupancy)
                  out_feature.setAttribute('peak_occupancy_time', datetime_to_unixtimestamp(str(self.date), str(self.peak_occupancy_time)))
                  out_feature.setAttribute('Capacity', self.capacity)
                  out_feature.setAttribute('week_start_date', self.week_start_date)
                  out_feature.setAttribute('week_end_date', self.week_end_date)
                  self.pyoutput(out_feature)
                  self.peak_occupancy = 0
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> CreateSQL_Fraser
CreateSQL_Fraser: PythonCaller
    HIDE_ATTRIBUTES = average_occupancy Capacity week_start_date week_end_date peak_occupancy peak_occupancy_time
    NEW_ATTRIBUTES = accumulated_data
    PYTHONSOURCE:
      import fme
      import fmeobjects
      import datetime
      import time

      class FeatureProcessor(object):
          """Template Class Interface:
          When using this class, make sure its name is set as the value of the 'Class
          to Process Features' transformer parameter.
          """

          def __init__(self):
              """Base constructor for class members."""
              self.accumulated_data = "("
              self.counter = 0
              pass

          def input(self, feature):

              self.counter = self.counter + 1

              # Get the required attributes from the feature
              average_occupancy = feature.getAttribute('average_occupancy')
              capacity = feature.getAttribute('Capacity')
              week_start_date = feature.getAttribute('week_start_date')
              week_end_date = feature.getAttribute('week_end_date')
              peak_occupancy = feature.getAttribute('peak_occupancy')
              peak_occupancy_time = feature.getAttribute('peak_occupancy_time')
              zone_id = feature.getAttribute('zone_id')


              # Concatenate the attributes into a single string
              feature_string = f"'{week_start_date}','{week_end_date}','{zone_id}',{average_occupancy},{peak_occupancy},{peak_occupancy_time},{capacity}"

              # Append the feature string to the accumulated string
              if self.accumulated_data:
                  self.accumulated_data += f"{feature_string}), ("

              if(self.counter == 999):
                  self.accumulated_data = self.accumulated_data[:-3]

                  # Create a new output feature with accumulated data
                  out_feature = fmeobjects.FMEFeature()
                  out_feature.setAttribute('accumulated_data', self.accumulated_data.strip())  # Remove trailing space
                  self.pyoutput(out_feature)

                  self.accumulated_data = "("
                  self.counter = 0

          def close(self):
              """This method is called once all the FME Features have been processed
              from input().
              """
              self.accumulated_data = self.accumulated_data[:-3]

              # Create a new output feature with accumulated data
              out_feature = fmeobjects.FMEFeature()
              out_feature.setAttribute('accumulated_data', self.accumulated_data.strip())  # Remove trailing space
              self.pyoutput(out_feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteNewStats_Fraser [INITIATOR]
WriteNewStats_Fraser: SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      ;WITH UniqueSource AS (
          SELECT   week_start_date,
                   week_end_date,
                   zone_id,
                   average_occupancy,
                   peak_occupancy,
                   peak_occupancy_time,
                   Capacity
          FROM (
              SELECT
                   week_start_date,
                   week_end_date,
                   zone_id,
                   average_occupancy,
                   peak_occupancy,
                   peak_occupancy_time,
                   Capacity,
                  ROW_NUMBER() OVER (PARTITION BY week_start_date, zone_id ORDER BY peak_occupancy) AS row_num
              FROM (VALUES
                  @Value(accumulated_data)
              ) AS source( week_start_date,
                           week_end_date,
                           zone_id,
                           average_occupancy,
                           peak_occupancy,
                           peak_occupancy_time,
                           Capacity)
          ) AS ranked
          WHERE row_num = 1
      )



      MERGE INTO [dbo].[Weekly_Occupancy_Stats] AS target
      USING UniqueSource AS source
      ON (target.week_start_date = source.week_start_date AND target.zone_id = source.zone_id)
      WHEN MATCHED THEN
          UPDATE SET
              target.average_occupancy = source.average_occupancy,
              target.peak_occupancy = source.peak_occupancy,
              target.peak_occupancy_time = source.peak_occupancy_time
      WHEN NOT MATCHED THEN
          INSERT ( week_start_date,
                   week_end_date,
                   zone_id,
                   average_occupancy,
                   peak_occupancy,
                   peak_occupancy_time,
                   Capacity )
          VALUES ( source.week_start_date,
                   source.week_end_date,
                   source.zone_id,
                   source.average_occupancy,
                   source.peak_occupancy,
                   source.peak_occupancy_time,
                   source.Capacity);
