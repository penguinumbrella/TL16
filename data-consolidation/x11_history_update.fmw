FME workspace x11_history_update.fmw

Creator
    GEOMTYPE = Geometry Object
    NUM = 1
    CREATED -> GetStallIds [INITIATOR]
GetStallIds: SQLExecutor
    COMBINE_ATTRS = Result Attributes Only
    COMBINE_GEOM = Initiator Geometry Only
    DATASET = AWS_UBCParking
    EXPOSED_ATTRIBUTE_LIST = stall_id,linked_date
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT = SELECT DISTINCT stall_id, linked_date from [x11_management]
    RESULT -> GetStallStats
GetStallStats: PythonCaller
    NEW_ATTRIBUTES = stall_id f_linked_date today
    PYTHONSOURCE:
      import fme
      import fmeobjects
      from datetime import datetime

      DATE_FORMAT = '%Y-%m-%d'

      class FeatureProcessor(object):
          """Template Class Interface:
          When using this class, make sure its name is set as the value of the 'Class
          to Process Features' transformer parameter.
          """

          def __init__(self):
              """Base constructor for class members."""
              pass

          def input(self, feature):
              stall_id = feature.getAttribute('stall_id')
              linked_date = feature.getAttribute('linked_date')

              # Separate into year, month, and day
              year = linked_date[:4]
              month = linked_date[4:6]
              day = linked_date[6:]

              year_num = int(year)

              # Some stall don't have an intallation date, or it sets to 1900 automatically,
              # which is obviously not true
              # These stalls do not return stats anyways, so they are ignored
              if year_num >= 2020:

                  # Format to desired date format (YYYY-MM-DD)
                  formatted_linked_date =f"{year}-{month}-{day}"

                  # Get today's date
                  today_date = datetime.now().strftime(DATE_FORMAT)

                  newFeature = fmeobjects.FMEFeature()
                  newFeature.setAttribute('stall_id', stall_id)
                  newFeature.setAttribute('f_linked_date', formatted_linked_date)
                  newFeature.setAttribute('today', today_date)
                  self.pyoutput(newFeature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> X11_Stall_Stats
X11_Stall_Stats: HTTPCaller
    CONNECTION_TIMEOUT_LENGTH = 60
    CUSTOM_HEADERS = Accept;application/json Authorization;Bearer eyJ0eXAiOiJKV1QiLCJhbGciOiJSUzI1NiJ9.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.LGrwl-yYHRViX8wTCPswtk1rGeb7VtCBMNqS78kj6vDJYY66tSnD0NW36eOHK5TL-1Mmmp9SGQDZgATSZSEj0hm2d8dZ9EXPab3jufUySlb4lLgauT8qNxQnoIjEGTSXsdHQu2mbd_97BtjF_yPDDW1Gsp01SBuLbI0uQoRkRKvUEuabFghzpV_01XmL7Lw8Fl3-T1lFI9cUfzGraKRfiePYrhM-z55xv9EfTfZSb5lFjgo8QSPNjCA0D5DJ00da67KWYQUZ4oubolr_ydR1dAbbpC9Whd3Twe--JRenHyxAwgpM0sBhkj7MZcaZ19Tvf1N52lgxwl-ocuWbdSoK6T4IkUdeM7wUARfo47GywiOMUwqMdSUt82bMk-AieGsysxZyWV_gAVx6ACxofx4UgMGTZC4PKql6sSi7onjc7Pt_vIb7Vj-oU2KtqPjCHCKlWOkgNFj5A4lCDMcNzFExSI89nWsvWqzhv7132yrLDWOpRBVP5o7rjXZ3jyGw06J6jCVRYwpNPlNs59qbP9TRb0IqQFg8FLAzMUt_Bx6EEFFmbUb3XzDtxdrfdfwel5ZrWtoE0QMGfObe5NxxYYHQDtpVpakBUWYkmNrbNUgvgxuJupe3QnM29s_YP6q-1XTAw1eoz9009a115iBuRUOIxjJs7iC8eBhxUWijuHD2Ksk
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://app.eleven-x.com/api/v2/stats/parking/stalls/@Value(stall_id)?from_date=@Value(f_linked_date)&to_date=@Value(today)&period_type=d
    TRANSFER_TIMEOUT_LENGTH = 90
    USE_COOKIES = No
    VERIFY_SSL_CERTIFICATES = Yes
    -> Extract_Stall_Stats
    -> ExtractStallHistory
Extract_Stall_Stats: PythonCaller
    HIDE_ATTRIBUTES = _response_body
    NEW_ATTRIBUTES = occupancy_percentage daily_state_change daily_parking_turnover avg_session_time avg_dwell_time stall_id
    PYTHONSOURCE:
      import fme
      import fmeobjects
      import json

      class FeatureProcessor(object):
          """Template Class Interface:
          When using this class, make sure its name is set as the value of the 'Class
          to Process Features' transformer parameter.
          """

          def __init__(self):
              """Base constructor for class members."""
              pass

          def input(self, feature):
              response = json.loads(feature.getAttribute('_response_body'))
              stall_stats = response.get("summary", {},)

              newFeature = fmeobjects.FMEFeature()
              newFeature.setAttribute('stall_id', feature.getAttribute('stall_id'))

               # Update location fields to be part of top level dictionary
              if 'occupancy_percentage' in stall_stats:
                  occupancy_percentage = stall_stats['occupancy_percentage']
                  newFeature.setAttribute('occupancy_percentage', occupancy_percentage)


              if 'daily_state_change' in stall_stats:
                  daily_state_change = stall_stats['daily_state_change']
                  newFeature.setAttribute('daily_state_change', daily_state_change)


              if 'daily_parking_turnover' in stall_stats:
                  daily_parking_turnover = stall_stats['daily_parking_turnover']
                  newFeature.setAttribute('daily_parking_turnover', daily_parking_turnover)


              if 'avg_session_time' in stall_stats:
                  avg_session_time = stall_stats['avg_session_time']
                  newFeature.setAttribute('avg_session_time', avg_session_time)

              if 'avg_dwell_time' in stall_stats:
                  avg_dwell_time = stall_stats['avg_dwell_time']
                  newFeature.setAttribute('avg_dwell_time', avg_dwell_time)


              self.pyoutput(newFeature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteStallStats [INITIATOR]
WriteStallStats: SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      -- Insert a new row into the table using the declared variables
      INSERT INTO dbo.x11_stall_stats (
      	stall_id,
      	occupancy_percentage,
      	daily_state_change,
      	daily_parking_turnover,
      	avg_session_time,
      	avg_dwell_time
      ) VALUES (
          @Value(stall_id),
          @Value(occupancy_percentage),
          @Value(daily_state_change),
          @Value(daily_parking_turnover),
          @Value(avg_session_time),
          @Value(avg_dwell_time)
      );

      MERGE dbo.x11_stall_stats AS target
      USING (VALUES
          (@Value(stall_id),
           @Value(occupancy_percentage),
           @Value(daily_state_change),
           @Value(daily_parking_turnover),
           @Value(avg_session_time),
           @Value(avg_dwell_time))
      ) AS source (stall_id, occupancy_percentage, daily_state_change, daily_parking_turnover, avg_session_time, avg_dwell_time)
      ON target.stall_id = source.stall_id
      WHEN MATCHED THEN
          UPDATE SET
              occupancy_percentage = source.occupancy_percentage,
              daily_state_change = source.daily_state_change,
              daily_parking_turnover = source.daily_parking_turnover,
              avg_session_time = source.avg_session_time,
              avg_dwell_time = source.avg_dwell_time
      WHEN NOT MATCHED THEN
          INSERT (stall_id, occupancy_percentage, daily_state_change, daily_parking_turnover, avg_session_time, avg_dwell_time)
          VALUES (source.stall_id, source.occupancy_percentage, source.daily_state_change, source.daily_parking_turnover, source.avg_session_time, source.avg_dwell_time);
ExtractStallHistory: PythonCaller
    HIDE_ATTRIBUTES = _response_body
    NEW_ATTRIBUTES = stall_id date car_in car_out car_count occupancy_percentage session_time dwell_time parking_turnover state_change
    PYTHONSOURCE:
      import fme
      import fmeobjects
      import json


      class FeatureProcessor(object):
          """Template Class Interface:
          When using this class, make sure its name is set as the value of the 'Class
          to Process Features' transformer parameter.
          """

          def __init__(self):
              self.feature_list = []

              pass

          def input(self, feature):
              response = json.loads(feature.getAttribute('_response_body'))
              stall_history = response.get("slicedData", [])
              stall_id = feature.getAttribute('stall_id')

              for day in stall_history:
                  newFeature = fmeobjects.FMEFeature()
                  newFeature.setAttribute('stall_id', stall_id)
                  newFeature.setAttribute('date', day.get('index'))
                  newFeature.setAttribute('car_in', day.get('car_in'))
                  newFeature.setAttribute('car_out', day.get('car_out'))
                  newFeature.setAttribute('car_count', day.get('car_count'))
                  newFeature.setAttribute('occupancy_percentage', day.get('occupancy_percentage'))
                  newFeature.setAttribute('session_time', day.get('session_time'))
                  newFeature.setAttribute('dwell_time', day.get('dwell_time'))
                  newFeature.setAttribute('parking_turnover', day.get('parking_turnover'))
                  newFeature.setAttribute('state_change', day.get('state_change'))

                  self.feature_list.append(newFeature)

          def close(self):
              for feature in self.feature_list:
                  self.pyoutput(feature)
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> WriteStallHistory [INITIATOR]
WriteStallHistory: SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      -- Insert a new row into the table using the declared variables
      INSERT INTO dbo.x11_stall_histories (
          stall_id,
          date,
          car_in,
          car_out,
          car_count,
          occupancy_percentage,
          session_time,
          dwell_time,
          parking_turnover,
          state_change
      ) VALUES (
          @Value(stall_id),
          '@Value(date)',
          @Value(car_in),
          @Value(car_out),
          @Value(car_count),
          @Value(occupancy_percentage),
          @Value(session_time),
          @Value(dwell_time),
          @Value(parking_turnover),
          @Value(state_change)
      );

      MERGE dbo.x11_stall_histories AS target
      USING (VALUES
          (@Value(stall_id),
           '@Value(date)',
           @Value(car_in),
           @Value(car_out),
           @Value(car_count),
           @Value(occupancy_percentage),
           @Value(session_time),
           @Value(dwell_time),
           @Value(parking_turnover),
           @Value(state_change))
      ) AS source (
          stall_id,
          date,
          car_in,
          car_out,
          car_count,
          occupancy_percentage,
          session_time,
          dwell_time,
          parking_turnover,
          state_change)
      ON target.stall_id = source.stall_id AND target.date = source.date
      WHEN MATCHED THEN
          UPDATE SET
              car_in = source.car_in,
              car_out = source.car_out,
              car_count = source.car_count,
              occupancy_percentage = source.occupancy_percentage,
              session_time = source.session_time,
              dwell_time = source.dwell_time,
              parking_turnover = source.parking_turnover,
              state_change = source.state_change
      WHEN NOT MATCHED THEN
          INSERT (stall_id, date, car_in, car_out, car_count, occupancy_percentage, session_time, dwell_time, parking_turnover, state_change)
          VALUES (source.stall_id, source.date, source.car_in, source.car_out, source.car_count, source.occupancy_percentage, source.session_time, source.dwell_time, source.parking_turnover, source.state_change);
ListBuilder
    LIST_ATTRS_TO_INCLUDE = car_count car_in car_out date dwell_time occupancy_percentage parking_turnover session_time stall_id state_change
    LIST_NAME = history_of_stall
ListConcatenator
    DROP_EMPTY_PARTS = No
    LIST_ATTR = history_of_stall{}
    SEP = ,
    VAL_ATTR = history_combined
WriteStallHistory_2: SQLExecutor
    COMBINE_ATTRS = Result Attributes Only
    COMBINE_GEOM = Initiator Geometry Only
    DATASET = AWS_UBCParking
    FORMAT = MSSQL_JDBC_NONSPATIAL_2
    MSSQL_JDBC_NONSPATIAL_2_APPLICATION_INTENT = ReadWrite
    MSSQL_JDBC_NONSPATIAL_2_CREATE_FEATURE_TABLES_FROM_DATA = Yes
    MSSQL_JDBC_NONSPATIAL_2_NAMED_CONNECTION = AWS_UBCParking
    MSSQL_JDBC_NONSPATIAL_2_QUERY_FEATURE_TYPES_FOR_MERGE_FILTERS = Yes
    MSSQL_JDBC_NONSPATIAL_2_QUERY_TIMEOUT = 30
    OUTPUT_FEATURES_DISPLAY = Schema and Data Features
    SQL_STATEMENT:
      -- Insert a new row into the table using the declared variables
      INSERT INTO dbo.x11_stall_histories (
          stall_id,
          date,
          car_in,
          car_out,
          car_count,
          occupancy_percentage,
          session_time,
          dwell_time,
          parking_turnover,
          state_change
      ) VALUES (
          @Value(stall_id),
          '@Value(date)',
          @Value(car_in),
          @Value(car_out),
          @Value(car_count),
          @Value(occupancy_percentage),
          @Value(session_time),
          @Value(dwell_time),
          @Value(parking_turnover),
          @Value(state_change)
      );

      MERGE dbo.x11_stall_histories AS target
      USING (VALUES
          (@Value(stall_id),
           '@Value(date)',
           @Value(car_in),
           @Value(car_out),
           @Value(car_count),
           @Value(occupancy_percentage),
           @Value(session_time),
           @Value(dwell_time),
           @Value(parking_turnover),
           @Value(state_change))
      ) AS source (
          stall_id,
          date,
          car_in,
          car_out,
          car_count,
          occupancy_percentage,
          session_time,
          dwell_time,
          parking_turnover,
          state_change)
      ON target.stall_id = source.stall_id AND target.date = source.date
      WHEN MATCHED THEN
          UPDATE SET
              car_in = source.car_in,
              car_out = source.car_out,
              car_count = source.car_count,
              occupancy_percentage = source.occupancy_percentage,
              session_time = source.session_time,
              dwell_time = source.dwell_time,
              parking_turnover = source.parking_turnover,
              state_change = source.state_change
      WHEN NOT MATCHED THEN
          INSERT (stall_id, date, car_in, car_out, car_count, occupancy_percentage, session_time, dwell_time, parking_turnover, state_change)
          VALUES (source.stall_id, source.date, source.car_in, source.car_out, source.car_count, source.occupancy_percentage, source.session_time, source.dwell_time, source.parking_turnover, source.state_change);
