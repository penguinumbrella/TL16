FME workspace weather.fmw

Creator
    GEOMTYPE = Geometry Object
    NUM = 1
    CREATED -> CreateForecastedTable [INITIATOR]
    CREATED -> CreateActualWeatherTable [INITIATOR]
CreateForecastedTable: SQLExecutor
    COMBINE_ATTRS = Result Attributes Only
    COMBINE_GEOM = Initiator Geometry Only
    DATASET = ServerTestDB
    EXPOSED_ATTRIBUTE_LIST = _creation_instance
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT:
      IF NOT EXISTS (SELECT * FROM INFORMATION_SCHEMA.TABLES WHERE TABLE_NAME = 'forecasted')
      BEGIN
          CREATE TABLE forecasted (
            uvi INT,
            visibility INT,
            wind_deg INT,
            wind_gust FLOAT,
            wind_speed FLOAT,
            temp FLOAT,
            pressure FLOAT,
            pop INT,
            feels_like FLOAT,
            dew_point FLOAT,
            clouds INT,
            dt BIGINT,
            snow FLOAT,
            rain FLOAT,
            weather_main VARCHAR(100),
            weather_desc VARCHAR(100)
          );
      END
    INITIATOR -> CallWeatherForecast
CallWeatherForecast: HTTPCaller
    ADDITIONAL_URL_PARAMETERS = lat;49.26 lon;-123.25 appid;608d7d3767d254be0d1a9ccd1e3c01c7 exclude;current,minutely,daily,alerts
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.openweathermap.org/data/3.0/onecall
    TRANSFER_TIMEOUT_LENGTH = 90
    USE_COOKIES = No
    VERIFY_SSL_CERTIFICATES = Yes
    -> TransformData
TransformData: PythonCaller
    HIDE_ATTRIBUTES = _creation_instance _http_status_code _response_body _matched_records
    NEW_ATTRIBUTES = uvi visibility wind_deg wind_gust wind_speed temp pressure pop feels_like dew_point clouds dt snow rain weather_main weather_desc
    PYTHONSOURCE:
      import fmeobjects
      import json


      class FeatureProcessor(object):
          """Template Class Interface:
          When using this class, make sure its name is set as the value of the 'Class
          to Process Features' transformer parameter.
          """

          def __init__(self):
              pass

          def input(self, feature):
              response = json.loads(feature.getAttribute('_response_body'))
              # newFeature = fmeobjects.FMEFeature()
              # newFeature.setAttribute('json', json.dumps(response))
              hourly = response['hourly']
              for data in hourly:
                  newFeature = fmeobjects.FMEFeature()
                  newFeature.setAttribute('snow', 0.0)
                  newFeature.setAttribute('rain', 0.0)
                  newFeature.setAttribute('wind_gust', 0.0)
                  for key in data:
                      if key == 'weather':
                         newFeature.setAttribute('weather_main', f"\'{data[key][0]['main']}\'")
                         newFeature.setAttribute('weather_desc', f"\'{data[key][0]['description']}\'")
                      elif key == 'rain':
                         newFeature.setAttribute('rain', data[key]['1h'])
                      elif key == 'snow':
                         newFeature.setAttribute('snow', data[key]['1h'])
                      else:
                         newFeature.setAttribute(key, data[key])
                  self.pyoutput(newFeature)

          def close(self):
              """This method is called at the end of the class."""
              pass
    PYTHONSYMBOL = FeatureProcessor
    -> PutForecasts [INITIATOR]
PutForecasts: SQLExecutor
    COMBINE_ATTRS = Result Attributes Only
    COMBINE_GEOM = Initiator Geometry Only
    DATASET = ServerTestDB
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT:
      IF NOT EXISTS (SELECT * FROM dbo.forecasted WHERE dt = @Value(dt))
      BEGIN
          INSERT INTO dbo.forecasted (uvi,
          visibility,
          wind_deg,
          wind_gust,
          wind_speed,
          temp,
          pressure,
          pop,
          feels_like,
          dew_point,
          clouds,
          dt,
          snow,
          rain,
          weather_main,
          weather_desc
          ) VALUES (@Value(uvi),
          @Value(visibility),
          @Value(wind_deg),
          @Value(wind_gust),
          @Value(wind_speed),
          @Value(temp),
          @Value(pressure),
          @Value(pop),
          @Value(feels_like),
          @Value(dew_point),
          @Value(clouds),
          @Value(dt),
          @Value(snow),
          @Value(rain),
          @Value(weather_main),
          @Value(weather_desc)
          );
      END
      ELSE
      BEGIN
          UPDATE dbo.forecasted
          SET uvi = @Value(uvi), visibility = @Value(visibility),
              wind_deg = @Value(wind_deg), wind_gust = @Value(wind_gust),
              wind_speed = @Value(wind_speed), temp = @Value(temp),
              pressure = @Value(pressure), pop = @Value(pop),
              feels_like = @Value(feels_like), dew_point = @Value(dew_point),
              clouds = @Value(clouds), dt = @Value(dt), snow = @Value(snow),
              rain = @Value(rain), weather_main = @Value(weather_main), weather_desc = @Value(weather_desc)
          WHERE dt = @Value(dt)
      END
CreateActualWeatherTable: SQLExecutor
    COMBINE_ATTRS = Result Attributes Only
    COMBINE_GEOM = Initiator Geometry Only
    DATASET = ServerTestDB
    EXPOSED_ATTRIBUTE_LIST = _creation_instance
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT:
      IF NOT EXISTS (SELECT * FROM INFORMATION_SCHEMA.TABLES WHERE TABLE_NAME = 'actual_weather')
      BEGIN
          CREATE TABLE actual_weather (
            uvi INT,
            visibility INT,
            wind_deg INT,
            wind_gust FLOAT,
            wind_speed FLOAT,
            temp FLOAT,
            pressure FLOAT,
            feels_like FLOAT,
            dew_point FLOAT,
            clouds INT,
            dt BIGINT,
            snow FLOAT,
            rain FLOAT,
            weather_main VARCHAR(100),
            weather_desc VARCHAR(100)
          );
      END
    INITIATOR -> GetLastTimestamp [INITIATOR]
GetLastTimestamp: SQLExecutor
    COMBINE_ATTRS = Result Attributes Only
    COMBINE_GEOM = Initiator Geometry Only
    DATASET = ServerTestDB
    EXPOSED_ATTRIBUTE_LIST = dt
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT:
      IF EXISTS (SELECT TOP(1) dt FROM actual_weather ORDER BY dt DESC)
          SELECT TOP(1) dt FROM actual_weather ORDER BY dt DESC
      ELSE
          SELECT 0 AS dt
    RESULT -> GetTimestamps
GetTimestamps: PythonCaller
    NEW_ATTRIBUTES = timestamp
    PYTHONSOURCE:
      import fmeobjects
      import json
      import time


      class FeatureProcessor(object):
          """Template Class Interface:
          When using this class, make sure its name is set as the value of the 'Class
          to Process Features' transformer parameter.
          """

          def __init__(self):
              pass

          def input(self, feature):
              LIMIT = 100
              countFeatures = 0
              curr_time = int(time.time())
              while(curr_time % 3600 != 0):
                  curr_time -= 1
              print(countFeatures < LIMIT)
              print(curr_time > int(feature.getAttribute('dt')))
              print(int(feature.getAttribute('dt')))
              while(countFeatures < LIMIT and curr_time > int(feature.getAttribute('dt'))):
                  newFeature = fmeobjects.FMEFeature()
                  newFeature.setAttribute('timestamp', curr_time)
                  self.pyoutput(newFeature)
                  countFeatures += 1
                  curr_time -= 3600
              pass

          def close(self):
              pass
    PYTHONSYMBOL = FeatureProcessor
    -> CallCurrentWeather
CallCurrentWeather: HTTPCaller
    ADDITIONAL_URL_PARAMETERS = lat;49.26 lon;-123.25 appid;608d7d3767d254be0d1a9ccd1e3c01c7 dt;@Value(timestamp)
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.openweathermap.org/data/3.0/onecall/timemachine
    TRANSFER_TIMEOUT_LENGTH = 90
    USE_COOKIES = No
    VERIFY_SSL_CERTIFICATES = Yes
    -> TransformData2
TransformData2: PythonCaller
    HIDE_ATTRIBUTES = _http_status_code _response_body timestamp
    NEW_ATTRIBUTES = uvi visibility wind_deg wind_gust wind_speed temp pressure feels_like dew_point clouds dt snow rain weather_main weather_desc
    PYTHONSOURCE:
      import fmeobjects
      import json


      class FeatureProcessor(object):
          """Template Class Interface:
          When using this class, make sure its name is set as the value of the 'Class
          to Process Features' transformer parameter.
          """

          def __init__(self):
              pass

          def input(self, feature):
              response = json.loads(feature.getAttribute('_response_body'))
              # newFeature = fmeobjects.FMEFeature()
              # newFeature.setAttribute('json', json.dumps(response))
              data = response['data'][0]
              newFeature = fmeobjects.FMEFeature()
              newFeature.setAttribute('snow', 0.0)
              newFeature.setAttribute('rain', 0.0)
              newFeature.setAttribute('wind_gust', 0.0)
              for key in data:
                 print(key)
                 if key == 'weather':
                      newFeature.setAttribute('weather_main', f"\'{data[key][0]['main']}\'")
                      newFeature.setAttribute('weather_desc', f"\'{data[key][0]['description']}\'")
                 elif key == 'rain':
                      newFeature.setAttribute('rain', data[key]['1h'])
                 elif key == 'snow':
                      newFeature.setAttribute('snow', data[key]['1h'])
                 else:
                      newFeature.setAttribute(key, data[key])
              self.pyoutput(newFeature)

          def close(self):
              """This method is called at the end of the class."""
              pass
    PYTHONSYMBOL = FeatureProcessor
    -> PutActualWeather [INITIATOR]
PutActualWeather: SQLExecutor
    COMBINE_ATTRS = Result Attributes Only
    COMBINE_GEOM = Initiator Geometry Only
    DATASET = ServerTestDB
    FORMAT = MSSQL_ADO
    MSSQL_ADO_APPLICATION_INTENT = ReadWrite
    MSSQL_ADO_COMMAND_TIMEOUT = 30
    MSSQL_ADO_CREATE_FEATURE_TABLES_FROM_DATA = Yes
    MSSQL_ADO_NAMED_CONNECTION = ServerTestDB
    MSSQL_ADO_QUERY_FEATURE_TYPES_FOR_MERGE_FILTERS = Yes
    OUTPUT_FEATURES_DISPLAY = Schema and Data Features
    SQL_STATEMENT:
      IF NOT EXISTS (SELECT * FROM dbo.actual_weather WHERE dt = @Value(dt))
      BEGIN
          INSERT INTO dbo.actual_weather (uvi,
          visibility,
          wind_deg,
          wind_gust,
          wind_speed,
          temp,
          pressure,
          feels_like,
          dew_point,
          clouds,
          dt,
          snow,
          rain,
          weather_main,
          weather_desc
          ) VALUES (@Value(uvi),
          @Value(visibility),
          @Value(wind_deg),
          @Value(wind_gust),
          @Value(wind_speed),
          @Value(temp),
          @Value(pressure),
          @Value(feels_like),
          @Value(dew_point),
          @Value(clouds),
          @Value(dt),
          @Value(snow),
          @Value(rain),
          @Value(weather_main),
          @Value(weather_desc)
          );
      END
      ELSE
      BEGIN
          UPDATE dbo.actual_weather
          SET uvi = @Value(uvi), visibility = @Value(visibility),
              wind_deg = @Value(wind_deg), wind_gust = @Value(wind_gust),
              wind_speed = @Value(wind_speed), temp = @Value(temp),
              pressure = @Value(pressure),
              feels_like = @Value(feels_like), dew_point = @Value(dew_point),
              clouds = @Value(clouds), dt = @Value(dt), snow = @Value(snow),
              rain = @Value(rain), weather_main = @Value(weather_main), weather_desc = @Value(weather_desc)
          WHERE dt = @Value(dt)
      END
